# -*- coding: utf-8 -*-
"""
=============================================================================
ANVIL CAD - Generate Drawing  (remodelled)
=============================================================================
From a 3D model (the active document or a browsed file) this builds a TechDraw
page on the BNC template with a projection group (Front / Top / Right + an
isometric) and automatically dimensions the orthographic views - one clean,
de-duplicated dimension per unique size (hole diameters, edge lengths, radii),
placed beside the geometry rather than piled at the view centre.
=============================================================================
"""

import os
import math
import FreeCAD
import FreeCADGui as Gui

try:
    from PySide2 import QtCore, QtGui, QtWidgets
except ImportError:
    from PySide import QtCore, QtGui
    QtWidgets = QtGui


# =============================================================================
# CONFIG
# =============================================================================
STANDARD_SCALES = [
    (50.0, "50:1"), (20.0, "20:1"), (10.0, "10:1"), (5.0, "5:1"), (2.0, "2:1"),
    (1.0, "1:1"), (0.5, "1:2"), (0.2, "1:5"), (0.1, "1:10"), (0.05, "1:20"),
    (0.02, "1:50"), (0.01, "1:100"), (0.005, "1:200"), (0.002, "1:500"),
    (0.001, "1:1000"),
]
PAPER_SIZES = {
    "A0": (1189, 841), "A1": (841, 594), "A2": (594, 420),
    "A3": (420, 297), "A4": (297, 210),
}
# (left, right, top, bottom) - right margin reserves the title-block strip
DRAWING_MARGINS = {
    "A0": (20, 170, 20, 20), "A1": (20, 160, 20, 20), "A2": (15, 155, 15, 15),
    "A3": (10, 155, 10, 10), "A4": (10, 150, 10, 10),
}
_TWO_PI = 2.0 * math.pi
_MAX_AUTO = 80


# =============================================================================
# SOURCE / TEMPLATE / SCALE HELPERS
# =============================================================================
def get_template_path(paper_size):
    fc_home = FreeCAD.getHomePath()
    res = FreeCAD.getResourceDir()
    names = ["{0}_BNC_Template.svg".format(paper_size),
             "BNC_{0}_Template.svg".format(paper_size),
             "{0}_Landscape_blank.svg".format(paper_size)]
    roots = [os.path.join(fc_home, "data", "Mod", "TechDraw", "Templates"),
             os.path.join(res, "Mod", "TechDraw", "Templates")]
    for root in roots:
        for n in names:
            p = os.path.join(root, n)
            if os.path.exists(p):
                return p
    for root in roots:
        p = os.path.join(root, "A4_Landscape_blank.svg")
        if os.path.exists(p):
            return p
    return None


def find_solid_objects(doc):
    """Return the top-level solids to draw.
    PartDesign bodies are represented by the Body (its tip shape); their
    internal features and sketches are skipped so geometry isn't drawn twice."""
    skip_types = ("App::Origin", "App::Line", "App::Plane", "App::Part",
                  "App::DocumentObjectGroup", "Sketcher::SketchObject")

    bodies = [o for o in doc.Objects if o.TypeId == "PartDesign::Body"]
    result = [b for b in bodies
              if getattr(getattr(b, "Shape", None), "Volume", 0) > 1e-6]

    # everything living inside a body (features, sketches) must be excluded
    inside_body = set()
    for b in bodies:
        try:
            for c in b.OutListRecursive:
                inside_body.add(c.Name)
        except Exception:
            pass

    for obj in doc.Objects:
        if obj in result:
            continue
        if obj.TypeId.startswith("TechDraw::"):
            continue
        if obj.TypeId.startswith("PartDesign::"):
            continue
        if obj.TypeId in skip_types or obj.Name in inside_body:
            continue
        shp = getattr(obj, "Shape", None)
        if shp is not None and getattr(shp, "Volume", 0) > 1e-6:
            result.append(obj)
    return result


def _bbox(solids):
    xmin = ymin = zmin = 1e18
    xmax = ymax = zmax = -1e18
    ok = False
    for o in solids:
        try:
            b = o.Shape.BoundBox
        except Exception:
            continue
        ok = True
        xmin, ymin, zmin = min(xmin, b.XMin), min(ymin, b.YMin), min(zmin, b.ZMin)
        xmax, ymax, zmax = max(xmax, b.XMax), max(ymax, b.YMax), max(zmax, b.ZMax)
    if not ok:
        return None
    return {"length": xmax - xmin, "width": ymax - ymin, "height": zmax - zmin}


def optimal_scale(bbox, paper_size):
    paper_w, paper_h = PAPER_SIZES[paper_size]
    ml, mr, mt, mb = DRAWING_MARGINS[paper_size]
    avail_w = paper_w - ml - mr
    avail_h = paper_h - mt - mb
    L, W, H = bbox["length"], bbox["width"], bbox["height"]
    span_w = max(L, 1.0) + max(H, 1.0) + 0.6 * max(L, W, H)
    span_h = max(H, 1.0) + max(W, 1.0) + 0.6 * max(L, W, H)
    fit = min(avail_w / span_w, avail_h / span_h) * 0.9 if span_w and span_h else 1.0
    for factor, _s in STANDARD_SCALES:
        if factor <= fit:
            return factor
    return STANDARD_SCALES[-1][0]


# =============================================================================
# AUTO-DIMENSION ENGINE  (shared with the Show Dimensions tool)
# =============================================================================
_ROUND_TIDS = ("Part::GeomCircle", "Part::GeomArcOfCircle", "Part::GeomEllipse",
               "Part::GeomArcOfEllipse", "Part::GeomBSplineCurve",
               "Part::GeomBezierCurve")
_LINE_TIDS = ("Part::GeomLine", "Part::GeomLineSegment")


def _is_closed(edge):
    try:
        if bool(edge.isClosed()):
            return True
    except Exception:
        pass
    try:
        return abs(edge.LastParameter - edge.FirstParameter) >= (_TWO_PI - 1e-3)
    except Exception:
        return False


def _edge_kind(edge):
    try:
        tid = edge.Curve.TypeId
    except Exception:
        return None
    if tid in _LINE_TIDS:
        return "line"
    if tid in _ROUND_TIDS:
        return "circle_full" if _is_closed(edge) else "circle_arc"
    return None


def _circ_r(p1, p2, p3):
    ax, ay, bx, by, cx, cy = p1.x, p1.y, p2.x, p2.y, p3.x, p3.y
    d = 2.0 * (ax * (by - cy) + bx * (cy - ay) + cx * (ay - by))
    if abs(d) < 1e-9:
        return None
    a2, b2, c2 = ax * ax + ay * ay, bx * bx + by * by, cx * cx + cy * cy
    ux = (a2 * (by - cy) + b2 * (cy - ay) + c2 * (ay - by)) / d
    uy = (a2 * (cx - bx) + b2 * (ax - cx) + c2 * (bx - ax)) / d
    return math.hypot(ax - ux, ay - uy)


def _radius_of(edge):
    try:
        crv = edge.Curve
        tid = crv.TypeId
    except Exception:
        return None
    if tid in ("Part::GeomCircle", "Part::GeomArcOfCircle"):
        try:
            return float(crv.Radius)
        except Exception:
            pass
    if tid in ("Part::GeomEllipse", "Part::GeomArcOfEllipse"):
        try:
            return (float(crv.MajorRadius) + float(crv.MinorRadius)) / 2.0
        except Exception:
            pass
    try:
        f, l = edge.FirstParameter, edge.LastParameter
        pts = [edge.valueAt(f + (l - f) * t) for t in (0.25, 0.5, 0.75)]
        return _circ_r(pts[0], pts[1], pts[2])
    except Exception:
        return None


def _value_sig(edge, kind):
    try:
        if kind == "line":
            return ("len", round(edge.Length, 2))
        r = _radius_of(edge)
        return (kind, round(r, 2)) if r is not None else None
    except Exception:
        return None


def _scale_of(view):
    try:
        s = view.getScale()
        if s:
            return float(s)
    except Exception:
        pass
    try:
        return float(view.Scale) or 1.0
    except Exception:
        return 1.0


def _visible_sigs(view):
    sigs = set()
    try:
        for e in view.getVisibleEdges():
            try:
                sigs.add((e.Curve.TypeId, round(e.Length, 1)))
            except Exception:
                pass
    except Exception:
        pass
    return sigs


def _all_edges_jobs(view):
    jobs = []
    vis = _visible_sigs(view)
    scale = _scale_of(view)
    seen = set()
    i = 0
    while i < 5000:
        try:
            edge = view.getEdgeByIndex(i)
        except Exception:
            break
        if edge is None:
            break
        kind = _edge_kind(edge)
        if kind:
            try:
                length = edge.Length
            except Exception:
                length = None
            vsig = ((edge.Curve.TypeId, round(length * scale, 1))
                    if length is not None else None)
            visible = (not vis) or (vsig in vis)
            dedup = _value_sig(edge, kind)
            if visible and (dedup is None or dedup not in seen):
                if dedup is not None:
                    seen.add(dedup)
                jobs.append((kind, "Edge%d" % i))
        i += 1
        if len(jobs) >= _MAX_AUTO:
            break
    return jobs


def _place(dim, dtype, idx):
    try:
        if dtype in ("Radius", "Diameter"):
            pts = dim.getArcPoints()
            c = pts[0]
            r = (pts[1] - c).Length or 5.0
            ang = math.radians(35.0 + (idx * 57.0) % 300.0)
            off = r + 9.0
            px, py = c.x + off * math.cos(ang), c.y + off * math.sin(ang)
        else:
            p1, p2 = dim.getLinearPoints()
            mx, my = (p1.x + p2.x) / 2.0, (p1.y + p2.y) / 2.0
            dx, dy = (p2.x - p1.x), (p2.y - p1.y)
            length = math.hypot(dx, dy) or 1.0
            nx, ny = -dy / length, dx / length
            if (nx * mx + ny * my) < 0:
                nx, ny = -nx, -ny
            off = 11.0 + 6.0 * (idx % 3)
            px, py = mx + nx * off, my + ny * off
        dim.X, dim.Y = px, -py
    except Exception:
        pass


def _safe_remove(doc, obj):
    try:
        doc.removeObject(obj.Name)
    except Exception:
        pass


def _dim_ok(dim, arc):
    try:
        st = dim.State
        st = st if isinstance(st, (list, tuple)) else [str(st)]
        if any(("Inval" in s) or ("rror" in s) for s in st):
            return False
    except Exception:
        pass
    try:
        pts = dim.getArcPoints() if arc else dim.getLinearPoints()
        if not pts:
            return False
    except Exception:
        return False
    try:
        if float(dim.getRawValue()) <= 1e-6:
            return False
    except Exception:
        pass
    return True


def _make_linear(doc, page, view, subname, idx):
    dim = doc.addObject("TechDraw::DrawViewDimension", "Dimension")
    dim.Type = "Distance"
    dim.MeasureType = "Projected"
    dim.References2D = [(view, [subname])]
    page.addView(dim)
    dim.recompute()
    _place(dim, "Distance", idx)
    dim.recompute()
    return dim


def _make_circular(doc, page, view, subname, idx, prefer_diameter):
    # Orthographic views show holes as true circles, so the projected value IS
    # the real size - no need for "True" (which warns when 3D refs are absent).
    if prefer_diameter:
        attempts = [("Diameter", "Projected"), ("Radius", "Projected")]
    else:
        attempts = [("Radius", "Projected")]
    for dtype, mtype in attempts:
        dim = doc.addObject("TechDraw::DrawViewDimension", "Dimension")
        dim.Type = dtype
        try:
            dim.MeasureType = mtype
        except Exception:
            pass
        dim.References2D = [(view, [subname])]
        page.addView(dim)
        try:
            dim.recompute()
        except Exception:
            pass
        if _dim_ok(dim, arc=True):
            _place(dim, dtype, idx)
            dim.recompute()
            return dim
        _safe_remove(doc, dim)
    return None


def _wait_ready(views, timeout=25.0):
    """TechDraw builds view geometry (HLR) on background threads, so edges are
    not available immediately after recompute(). Pump the event loop until every
    view reports visible edges (or the timeout elapses)."""
    import time
    start = time.time()
    while (time.time() - start) < timeout:
        try:
            Gui.updateGui()
        except Exception:
            pass
        ready = True
        for v in views:
            try:
                if not v.getVisibleEdges():
                    ready = False
                    break
            except Exception:
                ready = False
                break
        if ready:
            try:
                Gui.updateGui()
            except Exception:
                pass
            return True
        time.sleep(0.1)
    return False


def dimension_view(doc, page, view):
    """Auto-dimension one view; return count placed."""
    jobs = _all_edges_jobs(view)
    made = 0
    placed = set()
    for i, (kind, subname) in enumerate(jobs):
        try:
            if kind == "line":
                dim = _make_linear(doc, page, view, subname, i)
            else:
                dim = _make_circular(doc, page, view, subname, i,
                                     prefer_diameter=(kind == "circle_full"))
        except Exception:
            continue
        if dim is None:
            continue
        try:
            val = round(float(dim.getRawValue()), 2)
        except Exception:
            val = None
        key = (dim.Type, val)
        if val is not None and key in placed:
            _safe_remove(doc, dim)
            continue
        placed.add(key)
        made += 1
    return made


# =============================================================================
# DRAWING BUILD
# =============================================================================
# ProjGroup projection directions per layout choice.
LAYOUTS = {
    "std": ["Front", "Top", "Right", "FrontTopRight"],
    "front_iso": ["Front", "FrontTopRight"],
    "ortho": ["Front", "Top", "Right"],
    "iso": ["FrontTopRight"],
}
ORTHO_DIRS = ("Front", "Top", "Right", "Left", "Bottom", "Rear")


def build_drawing(doc, solids, paper_size, layout_key, dim_key):
    bbox = _bbox(solids)
    if not bbox:
        raise ValueError("The model has no solid geometry to draw.")
    scale = optimal_scale(bbox, paper_size)

    page = doc.addObject("TechDraw::DrawPage", "Page")
    tmpl = doc.addObject("TechDraw::DrawSVGTemplate", "Template")
    tpath = get_template_path(paper_size)
    if tpath:
        tmpl.Template = tpath
    page.Template = tmpl

    pg = doc.addObject("TechDraw::DrawProjGroup", "ProjGroup")
    page.addView(pg)
    pg.Source = solids
    try:
        pg.ProjectionType = "First Angle"
    except Exception:
        pass
    pg.ScaleType = "Custom"
    pg.Scale = scale

    dirs = LAYOUTS.get(layout_key, LAYOUTS["std"])
    for d in dirs:
        try:
            pg.addProjection(d)
        except Exception as exc:
            FreeCAD.Console.PrintWarning(
                "GenerateDrawing: projection %s failed (%s)\n" % (d, exc))

    # position the group in the drawing area (biased up so the first-angle
    # Top-below view stays on the sheet)
    paper_w, paper_h = PAPER_SIZES[paper_size]
    ml, mr, mt, mb = DRAWING_MARGINS[paper_size]
    cx = (ml + (paper_w - mr)) / 2.0
    cy = (mb + (paper_h - mt)) / 2.0
    pg.X = cx
    pg.Y = cy + (paper_h - mt - mb) * 0.12
    doc.recompute()

    # collect the projection items by direction
    items = {}
    for v in getattr(pg, "Views", []):
        try:
            items[v.Type] = v
        except Exception:
            pass

    # decide which views to dimension
    if dim_key == "none":
        to_dim = []
    elif dim_key == "front":
        to_dim = [items[d] for d in ("Front",) if d in items]
    else:  # ortho
        to_dim = [items[d] for d in ORTHO_DIRS if d in items]

    total = 0
    if to_dim:
        # HLR geometry is computed asynchronously — wait for the edges to exist
        _wait_ready(to_dim, timeout=25.0)
        for view in to_dim:
            try:
                total += dimension_view(doc, page, view)
            except Exception as exc:
                FreeCAD.Console.PrintWarning(
                    "GenerateDrawing: dimensioning failed (%s)\n" % exc)

    # Let the auto-distributed layout finish, then RELEASE the group: turning
    # AutoDistribute off keeps the views where they are but stops the group from
    # ever re-arranging ("collapsing") on later recomputes. After this, dragging
    # the Front/parent view moves the whole group rigidly (dependent views keep
    # their relative positions) and each dependent view can also be moved alone.
    try:
        _wait_ready(list(getattr(pg, "Views", [])), timeout=15.0)
        doc.recompute()
        pg.AutoDistribute = False
    except Exception:
        pass

    doc.recompute()
    try:
        page.recompute()
        for v in getattr(pg, "Views", []):
            v.requestPaint()
    except Exception:
        pass

    return page, scale, total


# =============================================================================
# DIALOG
# =============================================================================
class GenerateDialog(QtWidgets.QDialog):
    def __init__(self):
        super(GenerateDialog, self).__init__(Gui.getMainWindow())
        self.setWindowTitle("Generate Drawing")
        self.setMinimumWidth(460)
        self.result_opts = None
        self._build()

    def _build(self):
        lay = QtWidgets.QVBoxLayout(self)

        # source
        gb_src = QtWidgets.QGroupBox("3D model source")
        sv = QtWidgets.QVBoxLayout(gb_src)
        self.rb_active = QtWidgets.QRadioButton("Active document")
        self.rb_file = QtWidgets.QRadioButton("Browse 3D file (FCStd / STEP / ...)")
        doc = FreeCAD.ActiveDocument
        if doc and find_solid_objects(doc):
            self.rb_active.setChecked(True)
            self.rb_active.setText("Active document  (%s)" % doc.Label)
        else:
            self.rb_active.setEnabled(False)
            self.rb_file.setChecked(True)
        sv.addWidget(self.rb_active)
        sv.addWidget(self.rb_file)
        row = QtWidgets.QHBoxLayout()
        self.path_edit = QtWidgets.QLineEdit()
        self.path_edit.setPlaceholderText("path to 3D model file...")
        btn_browse = QtWidgets.QPushButton("Browse...")
        btn_browse.clicked.connect(self._browse)
        row.addWidget(self.path_edit, 1)
        row.addWidget(btn_browse)
        sv.addLayout(row)
        lay.addWidget(gb_src)

        # options
        form = QtWidgets.QFormLayout()
        self.cb_paper = QtWidgets.QComboBox()
        self.cb_paper.addItems(["A4", "A3", "A2", "A1", "A0"])
        self.cb_paper.setCurrentText("A3")
        form.addRow("Paper size:", self.cb_paper)

        self.cb_views = QtWidgets.QComboBox()
        self.cb_views.addItem("Front + Top + Right + Isometric", "std")
        self.cb_views.addItem("Front + Isometric", "front_iso")
        self.cb_views.addItem("Front + Top + Right", "ortho")
        self.cb_views.addItem("Isometric only", "iso")
        form.addRow("Views:", self.cb_views)

        self.cb_dim = QtWidgets.QComboBox()
        self.cb_dim.addItem("Orthographic views", "ortho")
        self.cb_dim.addItem("Front view only", "front")
        self.cb_dim.addItem("None", "none")
        form.addRow("Auto-dimension:", self.cb_dim)
        lay.addLayout(form)

        note = QtWidgets.QLabel(
            "Dimensions are placed on the orthographic views (accurate true "
            "sizes); the isometric view is kept as a pictorial reference.")
        note.setWordWrap(True)
        note.setStyleSheet("color:#777; font-size:11px;")
        lay.addWidget(note)

        bb = QtWidgets.QDialogButtonBox(
            QtWidgets.QDialogButtonBox.Ok | QtWidgets.QDialogButtonBox.Cancel)
        bb.accepted.connect(self._ok)
        bb.rejected.connect(self.reject)
        lay.addWidget(bb)

    def _browse(self):
        wd = ""
        try:
            wd = FreeCAD.ParamGet(
                "User parameter:BaseApp/Preferences/General").GetString(
                "WorkingDirectory", "")
        except Exception:
            pass
        fn, _f = QtWidgets.QFileDialog.getOpenFileName(
            self, "Select 3D model", wd,
            "3D models (*.FCStd *.fcstd *.step *.stp *.iges *.igs *.brep);;All files (*.*)")
        if fn:
            self.path_edit.setText(fn)
            self.rb_file.setChecked(True)

    def _ok(self):
        if self.rb_file.isChecked():
            p = self.path_edit.text().strip()
            if not p or not os.path.isfile(p):
                QtWidgets.QMessageBox.warning(
                    self, "Generate Drawing", "Please choose a valid 3D file.")
                return
        self.result_opts = {
            "source": "file" if self.rb_file.isChecked() else "active",
            "path": self.path_edit.text().strip(),
            "paper": self.cb_paper.currentText(),
            "layout": self.cb_views.currentData(),
            "dim": self.cb_dim.currentData(),
        }
        self.accept()


# =============================================================================
# MAIN
# =============================================================================
def main():
    dlg = GenerateDialog()
    if dlg.exec_() != QtWidgets.QDialog.Accepted or not dlg.result_opts:
        return
    opt = dlg.result_opts

    # resolve source doc + solids
    if opt["source"] == "file":
        try:
            doc = FreeCAD.openDocument(opt["path"])
        except Exception as exc:
            QtWidgets.QMessageBox.critical(
                None, "Generate Drawing",
                "Could not open the model:\n%s" % exc)
            return
    else:
        doc = FreeCAD.ActiveDocument

    solids = find_solid_objects(doc)
    if not solids:
        QtWidgets.QMessageBox.warning(
            None, "Generate Drawing",
            "No solid geometry found in the model.")
        return

    FreeCAD.setActiveDocument(doc.Name)
    App = FreeCAD
    App.setActiveTransaction("Generate drawing")
    try:
        page, scale, ndim = build_drawing(
            doc, solids, opt["paper"], opt["layout"], opt["dim"])
    except Exception as exc:
        import traceback
        FreeCAD.Console.PrintError(traceback.format_exc())
        App.closeActiveTransaction(True)
        QtWidgets.QMessageBox.critical(
            None, "Generate Drawing", "Generation failed:\n%s" % exc)
        return
    App.closeActiveTransaction()

    # open the page
    try:
        Gui.setActiveDocument(doc.Name)
        page.ViewObject.doubleClicked()
        Gui.SendMsgToActiveView("ViewFit")
    except Exception:
        pass

    FreeCAD.Console.PrintMessage(
        "ANVIL CAD: drawing generated (scale 1:%g, %d dimensions)\n"
        % (round(1.0 / scale, 3) if scale else 1, ndim))


main()
