import FreeCAD
import os
from PySide import QtGui

# -------------------------------------------------
# READ WORKING DIRECTORY
# -------------------------------------------------
params = FreeCAD.ParamGet("User parameter:BaseApp/Preferences/General")
working_dir = params.GetString("WorkingDirectory", "")

if not working_dir or not os.path.isdir(working_dir):
    FreeCAD.Console.PrintError("Working Directory not set or invalid!\n")
    raise Exception("Working Directory not set or invalid")

# Parameter group to store undo counters
save_params = FreeCAD.ParamGet("User parameter:BaseApp/Preferences/VersionSave")

# -------------------------------------------------
# HELPERS
# -------------------------------------------------
def latest_version(base):
    v = 1
    while os.path.exists(f"{base}.{v:03d}.FCStd"):
        v += 1
    return v - 1

def get_valid_name(doc):
    label = (doc.Label or "").strip()
    if (not label) or label.lower().startswith("unnamed"):
        name, ok = QtGui.QInputDialog.getText(
            None,
            "Enter File Name",
            "File name is not defined.\nPlease enter a file name:"
        )
        if not ok or not name.strip():
            raise Exception("File name required")
        label = name.strip().replace(" ", "_")
        doc.Label = label
    return label.replace(" ", "_")

def base_name(doc):
    if doc.FileName:
        name = os.path.basename(doc.FileName).replace(".FCStd", "")
        if "." in name:
            name = name.rsplit(".", 1)[0]  # strip .001 etc
        return name
    return get_valid_name(doc)

# -------------------------------------------------
# SAVE DOCUMENT WITH LINK-SAFE CHANGE DETECTION
# -------------------------------------------------
def save_doc(doc):
    name = base_name(doc)
    base = os.path.join(working_dir, name)

    last_v = latest_version(base)
    undo_now = int(getattr(doc, "UndoCount", 0))
    undo_key = f"{name}_Undo"
    last_undo = save_params.GetInt(undo_key, -1)

    # First version ever
    if last_v < 1:
        path = f"{base}.001.FCStd"
        doc.saveAs(path)
        save_params.SetInt(undo_key, undo_now)
        FreeCAD.Console.PrintMessage(f"{name} → Saved as .001\n")
        return

    changed = bool(getattr(doc, "Modified", False)) or (undo_now != last_undo)

    if changed:
        new_v = last_v + 1
        path = f"{base}.{new_v:03d}.FCStd"
        doc.saveAs(path)
        save_params.SetInt(undo_key, undo_now)
        FreeCAD.Console.PrintMessage(f"{name} → Modified → Saved as .{new_v:03d}\n")
    else:
        # CRITICAL: do NOT rewrite the existing file; it changes timestamps and forces link reloads
        FreeCAD.Console.PrintMessage(f"{name} → No changes → skipped save\n")

# -------------------------------------------------
# MAIN
# -------------------------------------------------
for doc in FreeCAD.listDocuments().values():
    try:
        save_doc(doc)
    except Exception as e:
        FreeCAD.Console.PrintError(str(e) + "\n")

FreeCAD.Console.PrintMessage(f"\n✔ Version save done in WD:\n{working_dir}\n")
