import FreeCAD
import os
import re
import zipfile
import xml.etree.ElementTree as ET
from datetime import datetime
from PySide import QtGui, QtCore, QtWidgets


def _build_preview_scene(fpath):
    """Build the Coin3D scene ONCE for an FCStd (shaded faces + crisp B-rep edge
    lines, a fixed orthographic camera framing the model's bounding SPHERE, and
    an SoTransform 'spin' about the model centre for rotation). Geometry is read
    from the embedded *.brp shapes. Returns a dict {root, cam, spin, base}, or
    None. Building once means drag-rotation only re-renders (no re-tessellation),
    and there is NO interactive widget (offscreen only) so it can't crash."""
    try:
        from pivy import coin
        import Part
        import math
    except Exception:
        return None
    try:
        z = zipfile.ZipFile(fpath)
        names = z.namelist()
    except Exception:
        return None

    # Load ONLY the FINAL body / part shapes, not intermediate feature shapes.
    # An FCStd stores <Feature>.Shape.brp for every feature (Pad, Pocket, ...)
    # AND <Body>.Shape.brp for the finished body. Loading feature shapes too
    # would overlay e.g. the solid Pad on top of the holed result and fill the
    # holes. So parse Document.xml for the PartDesign::Body / Part::Feature
    # object names and load only "<name>.Shape.brp".
    try:
        xml = z.read("Document.xml").decode("utf-8", "replace")
        obj_names = re.findall(
            r'<Object type="(?:PartDesign::Body|Part::Feature|'
            r'PartDesign::FeaturePython)"\s+name="([^"]+)"', xml)
    except Exception:
        obj_names = []

    lower_map = {n.lower(): n for n in names}
    targets = []
    for nm in obj_names:
        real = lower_map.get((nm + ".Shape.brp").lower())
        if real:
            targets.append(real)
    if not targets:
        # Fallback (older files / no bodies parsed): every *.Shape.brp solid.
        targets = [n for n in names if n.lower().endswith(".shape.brp")]

    seen, shapes = set(), []
    for n in targets:
        try:
            sh = Part.Shape()
            sh.importBrepFromString(z.read(n).decode("utf-8", "replace"))
            if sh.isNull() or not sh.Solids:
                continue
            bb = sh.BoundBox
            key = (round(sh.Volume, 3), round(bb.XLength, 2),
                   round(bb.YLength, 2), round(bb.ZLength, 2))
            if key in seen:
                continue
            seen.add(key)
            shapes.append(sh)
        except Exception:
            continue
    if not shapes:
        return None
    try:
        # combined bounds -> centre C, radius R (sphere the camera frames)
        xmn = ymn = zmn = 1e18
        xmx = ymx = zmx = -1e18
        for sh in shapes:
            b = sh.BoundBox
            xmn = min(xmn, b.XMin); ymn = min(ymn, b.YMin); zmn = min(zmn, b.ZMin)
            xmx = max(xmx, b.XMax); ymx = max(ymx, b.YMax); zmx = max(zmx, b.ZMax)
        C = coin.SbVec3f((xmn + xmx) / 2.0, (ymn + ymx) / 2.0, (zmn + zmx) / 2.0)
        R = 0.5 * math.sqrt((xmx - xmn) ** 2 + (ymx - ymn) ** 2 + (zmx - zmn) ** 2)
        if R <= 1e-6:
            R = 1.0

        root = coin.SoSeparator()
        cam = coin.SoOrthographicCamera()
        cam.position = coin.SbVec3f(C[0], C[1], C[2] + R * 4.0)
        cam.nearDistance = R * 2.0
        cam.farDistance = R * 6.0
        cam.focalDistance = R * 4.0
        cam.height = 2.0 * R * 1.15
        root.addChild(cam)
        key = coin.SoDirectionalLight()
        key.direction = (-0.35, -0.45, -1.0)
        key.intensity = 1.0
        root.addChild(key)
        fill = coin.SoDirectionalLight()
        fill.direction = (0.6, 0.4, -0.5)
        fill.intensity = 0.45
        root.addChild(fill)
        # spin transform (rotates the model about its centre; camera + lights,
        # added before it, stay fixed like a real turntable)
        spin = coin.SoTransform()
        spin.center = C
        root.addChild(spin)
        hints = coin.SoShapeHints()
        hints.vertexOrdering = coin.SoShapeHints.COUNTERCLOCKWISE
        hints.shapeType = coin.SoShapeHints.SOLID
        hints.creaseAngle = math.radians(35)
        root.addChild(hints)
        try:
            po = coin.SoPolygonOffset()
            po.styles = coin.SoPolygonOffset.FILLED
            po.factor = 1.2
            po.units = 3.0
            root.addChild(po)
        except Exception:
            pass

        for sh in shapes:
            diag = max(getattr(sh.BoundBox, "DiagonalLength", 0.0) or 0.0, 1e-3)
            f_defl = max(diag * 0.0035, 1e-3)
            e_defl = max(diag * 0.0025, 1e-3)
            try:
                pts, facets = sh.tessellate(f_defl)
            except Exception:
                pts, facets = None, None
            if pts and facets:
                fsep = coin.SoSeparator()
                fmat = coin.SoMaterial()
                fmat.ambientColor = (0.30, 0.32, 0.35)
                fmat.diffuseColor = (0.63, 0.67, 0.73)
                fmat.specularColor = (0.35, 0.35, 0.37)
                fmat.shininess = 0.35
                fsep.addChild(fmat)
                fc = coin.SoCoordinate3()
                fc.point.setValues(0, len(pts), [(p.x, p.y, p.z) for p in pts])
                fsep.addChild(fc)
                fset = coin.SoIndexedFaceSet()
                idx = []
                for t in facets:
                    idx += [t[0], t[1], t[2], -1]
                fset.coordIndex.setValues(0, len(idx), idx)
                fsep.addChild(fset)
                root.addChild(fsep)

            allpts, numv = [], []
            for edge in sh.Edges:
                epts = None
                try:
                    epts = edge.discretize(Deflection=e_defl)
                except Exception:
                    try:
                        epts = edge.discretize(28)
                    except Exception:
                        epts = None
                if not epts or len(epts) < 2:
                    continue
                numv.append(len(epts))
                allpts.extend([(p.x, p.y, p.z) for p in epts])
            if allpts:
                esep = coin.SoSeparator()
                ecol = coin.SoBaseColor()
                ecol.rgb = (0.16, 0.17, 0.19)
                esep.addChild(ecol)
                eds = coin.SoDrawStyle()
                eds.lineWidth = 1.3
                esep.addChild(eds)
                ec = coin.SoCoordinate3()
                ec.point.setValues(0, len(allpts), allpts)
                esep.addChild(ec)
                lset = coin.SoLineSet()
                lset.numVertices.setValues(0, len(numv), numv)
                esep.addChild(lset)
                root.addChild(esep)

        # default 3/4 (isometric-ish) view
        base = (coin.SbRotation(coin.SbVec3f(1, 0, 0), math.radians(-60))
                * coin.SbRotation(coin.SbVec3f(0, 0, 1), math.radians(45)))
        return {"root": root, "cam": cam, "spin": spin, "base": base}
    except Exception:
        return None


def _set_scene_rotation(scene, azim, elev):
    """Orbit the model: yaw by azim, pitch by elev (radians), on top of the
    default iso view."""
    try:
        from pivy import coin
        orbit = (coin.SbRotation(coin.SbVec3f(1, 0, 0), elev)
                 * coin.SbRotation(coin.SbVec3f(0, 1, 0), azim))
        scene["spin"].rotation.setValue(orbit * scene["base"])
    except Exception:
        pass


# Offscreen renderers are cached by pixel size and reused across frames, so a
# drag doesn't create/destroy a GL context every mouse-move (that would lag).
_RENDERERS = {}


def _render_scene(scene, disp, supersample=True):
    """Offscreen-render the cached scene to a QPixmap at display size `disp`.
    supersample=True renders at 2x then downscales (antialiased) for the final
    view; drag frames use supersample=False for responsiveness."""
    try:
        from pivy import coin
    except Exception:
        return None
    try:
        rsz = disp * 2 if supersample else disp
        entry = _RENDERERS.get(rsz)
        if entry is None:
            rnd = coin.SoOffscreenRenderer(coin.SbViewportRegion(rsz, rsz))
            fmt = QtGui.QImage.Format_RGBA8888
            try:
                rnd.setComponents(rnd.RGB_TRANSPARENCY)
            except Exception:
                fmt = QtGui.QImage.Format_RGB888
            rnd.setBackgroundColor(coin.SbColor(0.906, 0.906, 0.906))
            _RENDERERS[rsz] = (rnd, fmt)
        else:
            rnd, fmt = entry
        if not rnd.render(scene["root"]):
            return None
        buf = bytes(rnd.getBuffer())
        img = QtGui.QImage(buf, rsz, rsz, fmt).copy()
        img = img.mirrored(False, True)   # GL buffer is bottom-up
        if supersample and rsz != disp:
            img = img.scaled(disp, disp, QtCore.Qt.KeepAspectRatio,
                             QtCore.Qt.SmoothTransformation)
        return QtGui.QPixmap.fromImage(img)
    except Exception:
        return None


class PreviewLabel(QtWidgets.QLabel):
    """QLabel that reports left-button drags so the 3D preview can be rotated."""

    def __init__(self, *args, **kwargs):
        super().__init__(*args, **kwargs)
        self._drag = False
        self._lx = 0
        self._ly = 0
        self.on_rotate = None       # callback(dx, dy)
        self.on_rotate_end = None   # callback()

    @staticmethod
    def _xy(ev):
        # position() is the non-deprecated accessor (PySide6); fall back to pos().
        try:
            p = ev.position()
            return int(p.x()), int(p.y())
        except Exception:
            p = ev.pos()
            return p.x(), p.y()

    def mousePressEvent(self, ev):
        if ev.button() == QtCore.Qt.LeftButton:
            self._drag = True
            self._lx, self._ly = self._xy(ev)
            self.setCursor(QtCore.Qt.ClosedHandCursor)

    def mouseMoveEvent(self, ev):
        if self._drag:
            x, y = self._xy(ev)
            dx, dy = x - self._lx, y - self._ly
            self._lx, self._ly = x, y
            if callable(self.on_rotate):
                self.on_rotate(dx, dy)

    def mouseReleaseEvent(self, ev):
        if self._drag:
            self._drag = False
            self.setCursor(QtCore.Qt.OpenHandCursor)
            if callable(self.on_rotate_end):
                self.on_rotate_end()


# -------------------------------------------------
# WORKING DIRECTORY
# -------------------------------------------------
params = FreeCAD.ParamGet("User parameter:BaseApp/Preferences/General")
wd = params.GetString("WorkingDirectory", "")

if not wd or not os.path.isdir(wd):
    FreeCAD.Console.PrintError("Working Directory not set\n")
    raise Exception("WD not set")

# -------------------------------------------------
# HELPERS
# -------------------------------------------------
# Match both naming conventions:
#   Name.001.FCStd            (old Version_Save)
#   Name.001.asm.FCStd        (Save macro — logical .prt/.asm/.drg ext)
version_re = re.compile(r"(.+)\.(\d{3})(?:\.(prt|asm|drg))?\.FCStd$", re.IGNORECASE)


def scan_files(directory, show_all=False):
    versioned = []
    unversioned = []
    latest = {}

    for f in os.listdir(directory):
        if not f.lower().endswith('.fcstd'):
            continue
        full = os.path.join(directory, f)
        m = version_re.match(f)
        if m:
            base = m.group(1)
            v = int(m.group(2))
            ext = (m.group(3) or "").lower()
            # Group versions of the SAME logical file (same base AND same ext)
            # so '123.001.asm' and '123.002.asm' collapse to the latest, while
            # '123.001.asm' and '123.001.prt' stay distinct.
            key = base + "|" + ext
            versioned.append((f, full, key, v))
            if key not in latest or v > latest[key][1]:
                latest[key] = (full, v)
        else:
            unversioned.append((f, full, f, 0))

    if show_all:
        result = versioned + unversioned
    else:
        # versioned: show only the latest version per logical file
        result = [item for item in versioned
                  if latest.get(item[2], (None,))[0] == item[1]]
        result += unversioned  # non-versioned files always shown

    return sorted(result, key=lambda x: x[0].lower())


def get_description(filepath):
    """Read Comment property from Document.xml inside FCStd zip."""
    try:
        with zipfile.ZipFile(filepath, 'r') as zf:
            names = zf.namelist()
            doc_entry = next((n for n in names if n.endswith('Document.xml')), None)
            if doc_entry is None:
                return ""
            raw = zf.read(doc_entry)
            try:
                root = ET.fromstring(raw)
            except ET.ParseError:
                root = ET.fromstring(raw.decode('utf-8', errors='replace'))
            for prop in root.iter('Property'):
                if prop.get('name') == 'Comment':
                    s = prop.find('String')
                    if s is not None:
                        return s.get('value', '').strip()
                    return (prop.text or '').strip()
    except Exception as e:
        FreeCAD.Console.PrintError(f"get_description({os.path.basename(filepath)}): {e}\n")
    return ""


def get_fcstd_info(filepath):
    thumbnail = None
    description = get_description(filepath)
    try:
        with zipfile.ZipFile(filepath, 'r') as zf:
            names = zf.namelist()
            thumb = next((n for n in names if n.lower() == 'thumbnails/thumbnail.png'), None)
            if thumb:
                data = zf.read(thumb)
                pix = QtGui.QPixmap()
                pix.loadFromData(data)
                thumbnail = pix
    except Exception as e:
        FreeCAD.Console.PrintError(f"get_fcstd_info({os.path.basename(filepath)}): {e}\n")
    return thumbnail, description


# -------------------------------------------------
# DIALOG
# -------------------------------------------------
class OpenFileDialog(QtWidgets.QDialog):
    def __init__(self, working_dir):
        super().__init__(None, QtCore.Qt.Window)
        self.working_dir = working_dir
        self.selected_file = None
        self._cache = {}
        self.setWindowTitle("Open File")
        self.resize(1000, 620)
        self._build_ui()
        self._refresh()

    def _build_ui(self):
        root = QtWidgets.QVBoxLayout(self)
        root.setSpacing(8)
        root.setContentsMargins(12, 12, 12, 12)

        # ── path bar ──────────────────────────────────────────
        path_bar = QtWidgets.QHBoxLayout()
        parts = self.working_dir.replace("\\", "/").rstrip("/").split("/")
        path_text = "  >  ".join(p for p in parts if p)
        lbl = QtWidgets.QLabel(path_text)
        lbl.setStyleSheet("font-weight: bold; padding: 4px 8px;"
                          "background:#f0f0f0; border:1px solid #ccc; border-radius:3px;")
        self.search_box = QtWidgets.QLineEdit()
        self.search_box.setPlaceholderText("Search...")
        self.search_box.setFixedWidth(220)
        self.search_box.textChanged.connect(self._refresh)
        path_bar.addWidget(lbl, 1)
        path_bar.addWidget(self.search_box)
        root.addLayout(path_bar)

        # ── list + preview ────────────────────────────────────
        mid = QtWidgets.QHBoxLayout()
        mid.setSpacing(10)

        self.table = QtWidgets.QTableWidget()
        self.table.setColumnCount(2)
        self.table.setHorizontalHeaderLabels(["Name", "Description"])
        hh = self.table.horizontalHeader()
        hh.setSectionResizeMode(0, QtWidgets.QHeaderView.Stretch)
        hh.setSectionResizeMode(1, QtWidgets.QHeaderView.Fixed)
        self.table.setColumnWidth(1, 240)
        self.table.setSelectionBehavior(QtWidgets.QAbstractItemView.SelectRows)
        self.table.setSelectionMode(QtWidgets.QAbstractItemView.SingleSelection)
        self.table.setEditTriggers(QtWidgets.QAbstractItemView.NoEditTriggers)
        self.table.verticalHeader().setVisible(False)
        self.table.setAlternatingRowColors(True)
        self.table.setShowGrid(False)
        self.table.itemSelectionChanged.connect(self._on_select)
        self.table.doubleClicked.connect(self._on_open)
        mid.addWidget(self.table, 2)

        self.preview_panel = PreviewLabel("No Preview")
        self.preview_panel.setFixedSize(300, 300)
        self.preview_panel.setAlignment(QtCore.Qt.AlignCenter)
        self.preview_panel.setStyleSheet(
            "background:#e8e8e8; border:1px solid #bbb; border-radius:4px;"
            "color:#888; font-size:13px;")
        self.preview_panel.setToolTip("Drag to rotate")
        self.preview_panel.on_rotate = self._on_preview_drag
        self.preview_panel.on_rotate_end = self._on_preview_drag_end
        mid.addWidget(self.preview_panel)

        # Interactive 3D preview state
        self._preview_px = 300
        self._scene = None
        self._azim = 0.0
        self._elev = 0.0

        root.addLayout(mid, 1)

        # ── info bar (hidden until "Show details" checked) ────────
        self.info_bar = QtWidgets.QLabel("")
        self.info_bar.setStyleSheet(
            "background:#f7f7f7; border:1px solid #ddd; padding:5px 8px;"
            "border-radius:3px; color:#555;")
        self.info_bar.setTextFormat(QtCore.Qt.PlainText)
        self.info_bar.setVisible(False)
        root.addWidget(self.info_bar)

        # ── file name / type row ──────────────────────────────
        form = QtWidgets.QFormLayout()
        form.setSpacing(6)
        self.fname_edit = QtWidgets.QLineEdit()
        self.fname_edit.setReadOnly(True)
        self.fname_edit.setStyleSheet("padding:4px;")
        form.addRow("File name:", self.fname_edit)
        self.type_combo = QtWidgets.QComboBox()
        self.type_combo.addItem("All types", None)
        self.type_combo.addItem("Part (*.prt)", "prt")
        self.type_combo.addItem("Assembly (*.asm)", "asm")
        self.type_combo.addItem("Drawing (*.drg)", "drg")
        self.type_combo.currentIndexChanged.connect(self._refresh)
        form.addRow("Type:", self.type_combo)
        root.addLayout(form)

        # ── footer: checkboxes + buttons ──────────────────────
        footer = QtWidgets.QHBoxLayout()
        self.chk_all = QtWidgets.QCheckBox("Show all versions")
        self.chk_details = QtWidgets.QCheckBox("Show details")
        self.chk_preview = QtWidgets.QCheckBox("Preview")
        # Connect signals BEFORE setChecked so handlers fire on init
        self.chk_all.toggled.connect(self._refresh)
        self.chk_details.toggled.connect(self._on_toggle_details)
        self.chk_preview.toggled.connect(self._on_toggle_preview)
        self.chk_preview.setChecked(True)   # fires _on_toggle_preview(True)

        btn_open = QtWidgets.QPushButton("Open")
        btn_open.setFixedHeight(34)
        btn_open.setStyleSheet(
            "QPushButton{background:#c0392b;color:white;font-weight:bold;"
            "padding:0 28px;border-radius:3px;}"
            "QPushButton:hover{background:#e74c3c;}"
            "QPushButton:pressed{background:#96281b;}")
        btn_open.clicked.connect(self._on_open)

        btn_cancel = QtWidgets.QPushButton("Cancel")
        btn_cancel.setFixedHeight(34)
        btn_cancel.setStyleSheet(
            "QPushButton{padding:0 18px;border-radius:3px;"
            "border:1px solid #aaa;background:#fafafa;}"
            "QPushButton:hover{background:#eee;}")
        btn_cancel.clicked.connect(self.reject)

        footer.addWidget(self.chk_all)
        footer.addWidget(self.chk_details)
        footer.addWidget(self.chk_preview)
        footer.addStretch()
        footer.addWidget(btn_open)
        footer.addWidget(btn_cancel)
        root.addLayout(footer)

        # Description column is always visible; no hidden columns

    # ── slots ─────────────────────────────────────────────────

    def _refresh(self):
        search = self.search_box.text().lower()
        files = scan_files(self.working_dir, self.chk_all.isChecked())
        if search:
            files = [f for f in files if search in f[0].lower()]
        # Filter by logical type (.prt / .asm / .drg) chosen in the Type combo.
        sel_ext = self.type_combo.currentData() if hasattr(self, "type_combo") else None
        if sel_ext:
            def _ext_of(fn):
                m = version_re.match(fn)
                return (m.group(3) or "").lower() if m else ""
            files = [f for f in files if _ext_of(f[0]) == sel_ext]
        self._files = files
        self.table.setRowCount(len(files))
        for row, (fname, fpath, base, ver) in enumerate(files):
            # Hide the .FCStd container extension in the display (the real
            # path in UserRole is unchanged, so opening still works).
            item_n = QtWidgets.QTableWidgetItem(
                re.sub(r"\.FCStd$", "", fname, flags=re.IGNORECASE))
            item_n.setData(QtCore.Qt.UserRole, fpath)
            item_d = QtWidgets.QTableWidgetItem(self._cache.get(fpath, {}).get('desc', ''))
            self.table.setItem(row, 0, item_n)
            self.table.setItem(row, 1, item_d)
        # Load descriptions after the list is rendered
        QtCore.QTimer.singleShot(0, self._load_descriptions)

    def _load_descriptions(self):
        """Load description text for every row (fast zip read, no thumbnail)."""
        for row in range(self.table.rowCount()):
            item = self.table.item(row, 0)
            if not item:
                continue
            fpath = item.data(QtCore.Qt.UserRole)
            if fpath not in self._cache:
                desc = get_description(fpath)
                self._cache[fpath] = {'thumb': None, 'desc': desc, 'mtime': ''}
            d_item = self.table.item(row, 1)
            if d_item:
                d_item.setText(self._cache[fpath].get('desc', ''))

    def _on_select(self):
        row = self.table.currentRow()
        item = self.table.item(row, 0)
        if not item:
            return
        fpath = item.data(QtCore.Qt.UserRole)
        self.selected_file = fpath
        self.fname_edit.setText(
            re.sub(r"\.FCStd$", "", os.path.basename(fpath), flags=re.IGNORECASE))

        cached = self._cache.get(fpath, {})
        # Load full info if thumbnail not yet fetched
        # (_load_descriptions pre-fills cache with thumb=None, so we must check)
        if cached.get('thumb') is None:
            thumb, desc = get_fcstd_info(fpath)
            try:
                mtime = datetime.fromtimestamp(
                    os.path.getmtime(fpath)).strftime("%d-%b-%Y %I:%M:%S %p")
            except Exception:
                mtime = cached.get('mtime', '')
            self._cache[fpath] = {
                'thumb': thumb,
                'desc': cached.get('desc') or desc,
                'mtime': mtime,
            }
            # Update description cell if we got a better value
            if not cached.get('desc') and desc:
                d_item = self.table.item(row, 1)
                if d_item:
                    d_item.setText(desc)

        info = self._cache[fpath]
        if self.chk_details.isChecked():
            self.info_bar.setText(
                f"File name: {os.path.basename(fpath)}    "
                f"Date modified: {info['mtime']}    "
                f"Description: {info['desc']}")

        if self.chk_preview.isChecked():
            self._show_preview(fpath)

    def _show_preview(self, fpath):
        # Build (once) an interactive 3D scene and render it; the user can drag
        # to rotate. Fall back to the FCStd's stored thumbnail if the scene can't
        # be built. Scene is cached per file.
        self._scene = None
        pixmap = None
        if fpath:
            cache = self._cache.get(fpath, {})
            if 'scene3d' not in cache:
                cache['scene3d'] = _build_preview_scene(fpath)
                self._cache[fpath] = cache
            scene = cache.get('scene3d')
            if scene is not None:
                self._scene = scene
                self._azim, self._elev = 0.0, 0.0
                _set_scene_rotation(scene, self._azim, self._elev)
                pixmap = _render_scene(scene, self._preview_px, True)
            if pixmap is None or pixmap.isNull():
                pixmap = cache.get('thumb')   # fallback: stored thumbnail
        if pixmap and not pixmap.isNull():
            if self._scene is not None:
                self.preview_panel.setPixmap(pixmap)       # already display size
            else:
                self.preview_panel.setPixmap(pixmap.scaled(
                    self.preview_panel.size(),
                    QtCore.Qt.KeepAspectRatio,
                    QtCore.Qt.SmoothTransformation))
            self.preview_panel.setText("")
            self.preview_panel.setCursor(
                QtCore.Qt.OpenHandCursor if self._scene is not None
                else QtCore.Qt.ArrowCursor)
        else:
            self.preview_panel.setPixmap(QtGui.QPixmap())
            self.preview_panel.setText("No Preview")
            self.preview_panel.setCursor(QtCore.Qt.ArrowCursor)

    def _on_preview_drag(self, dx, dy):
        if self._scene is None:
            return
        self._azim += dx * 0.012
        self._elev += dy * 0.012
        if self._elev > 1.45:
            self._elev = 1.45
        elif self._elev < -1.45:
            self._elev = -1.45
        _set_scene_rotation(self._scene, self._azim, self._elev)
        pm = _render_scene(self._scene, self._preview_px, False)   # fast frame
        if pm is not None and not pm.isNull():
            self.preview_panel.setPixmap(pm)
            self.preview_panel.setText("")

    def _on_preview_drag_end(self):
        if self._scene is None:
            return
        pm = _render_scene(self._scene, self._preview_px, True)    # crisp frame
        if pm is not None and not pm.isNull():
            self.preview_panel.setPixmap(pm)
            self.preview_panel.setText("")

    def _on_toggle_preview(self, checked):
        self.preview_panel.setVisible(checked)
        if checked and self.selected_file:
            self._show_preview(self.selected_file)

    def _on_toggle_details(self, checked):
        self.info_bar.setVisible(checked)

    def _on_open(self):
        if self.selected_file:
            self.accept()
        else:
            QtWidgets.QMessageBox.warning(self, "No file selected",
                                          "Please select a file first.")


# -------------------------------------------------
# RUN
# -------------------------------------------------
dlg = OpenFileDialog(wd)
if dlg.exec():
    fp = dlg.selected_file
    if fp:
        FreeCAD.openDocument(fp)
        FreeCAD.Console.PrintMessage(f"Opened: {os.path.basename(fp)}\n")
