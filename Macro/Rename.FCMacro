import FreeCAD as App
import FreeCADGui as Gui
from PySide import QtGui
import os
import re
import zipfile
import json

_RENAME_MAP_FILE = os.path.join(os.path.dirname(os.path.abspath(__file__)),
                                '.rename_map.json')


def _write_rename_entry(old_name, new_name):
    """Append an old_name -> new_name entry to the shared rename-map file."""
    data = {}
    if os.path.exists(_RENAME_MAP_FILE):
        try:
            with open(_RENAME_MAP_FILE, 'r', encoding='utf-8') as f:
                data = json.load(f)
        except Exception:
            data = {}
    data[old_name] = new_name
    with open(_RENAME_MAP_FILE, 'w', encoding='utf-8') as f:
        json.dump(data, f, indent=2)


def _parse_versioned_name(filename):
    """Parse a versioned FCStd filename tolerantly.

    Returns (base_name, version, logical_ext, conforming).
    Accepts, in order of preference:
        BaseName.NNN.ext.FCStd   -> conforming (ext in prt|asm|drg)
        BaseName.NNN.FCStd       -> ext defaults to 'prt'  (non-conforming)
        BaseName.FCStd           -> version '001', ext 'prt' (non-conforming)
    Returns (None, None, None, False) if it is not an .FCStd file at all.
    """
    m = re.match(r"^(.*)\.(\d{3})\.(prt|asm|drg)\.FCStd$", filename, re.IGNORECASE)
    if m:
        return m.group(1), m.group(2), m.group(3).lower(), True
    m = re.match(r"^(.*)\.(\d{3})\.FCStd$", filename, re.IGNORECASE)
    if m:
        return m.group(1), m.group(2), "prt", False
    m = re.match(r"^(.*)\.FCStd$", filename, re.IGNORECASE)
    if m:
        return m.group(1), "001", "prt", False
    return None, None, None, False


def _is_root_assembly(obj):
    """Return True if obj is the top-level (root) Assembly in the document."""
    if obj.TypeId != 'Assembly::AssemblyObject':
        return False
    # A root assembly has no parent that is also an Assembly
    for parent in obj.InList:
        if parent.TypeId == 'Assembly::AssemblyObject':
            return False          # it's nested -> sub-assembly
    return True


def apply_info_to_first_body(doc, name, description):
    """Set Label and Description on the first PartDesign::Body or root
    Assembly::AssemblyObject in the document, whichever comes first."""
    for obj in doc.Objects:
        if obj.TypeId in ('PartDesign::Body', 'Assembly::AssemblyObject'):
            obj.Label = name
            if not hasattr(obj, 'Description'):
                obj.addProperty('App::PropertyString', 'Description',
                                'Base', 'Description')
            obj.Description = description
            if hasattr(obj, 'MP_Description'):
                obj.MP_Description = description
            break  # only the first matching object


def _read_obj_description(obj):
    """Effective description of a Body/Assembly object, matching the priority
    the Model Parameters macro uses: plain .Description first, then the
    MP_Description property (Model Parameters stores the value there)."""
    if hasattr(obj, "Description") and obj.Description:
        return obj.Description
    if hasattr(obj, "MP_Description") and obj.MP_Description:
        return obj.MP_Description
    return ""


def _effective_description(container_doc):
    """Description to pre-fill in the Rename dialog. Reads the first
    Body/Assembly object (where Model Parameters writes MP_Description) before
    falling back to the document-level Description / Comment, so a description
    entered via Model Parameters shows up here too."""
    for obj in container_doc.Objects:
        if obj.TypeId in ('PartDesign::Body', 'Assembly::AssemblyObject'):
            d = _read_obj_description(obj)
            if d:
                return d
            break  # only the first matching object
    # Model Parameters stores MP_Description on the DOCUMENT when it is run
    # with nothing selected (get_target() falls back to App.ActiveDocument).
    if hasattr(container_doc, "MP_Description") and container_doc.MP_Description:
        return container_doc.MP_Description
    if hasattr(container_doc, "Description") and container_doc.Description:
        return container_doc.Description
    if hasattr(container_doc, "Comment") and container_doc.Comment:
        return container_doc.Comment
    return ""


def main():
    # ============================================================
    # VALIDATE ACTIVE DOCUMENT
    # ============================================================

    doc = App.ActiveDocument
    if not doc:
        QtGui.QMessageBox.warning(None, "Error", "No Active Document.")
        return

    # ============================================================
    # DETERMINE TARGET: INTERNAL OBJECT / LINKED COMPONENT / TOP-LEVEL
    # ============================================================
    # rename_mode:
    #   "document" -- rename the top-level document (file on disk)
    #   "linked"   -- rename an externally-linked part/sub-assembly file
    #   "internal" -- rename a Body/Part created inside the current assembly
    # ============================================================

    rename_mode = "document"
    target_doc = doc
    parent_doc = None
    link_obj = None
    selected_obj = None

    # Types that should NOT be offered for rename (utility objects)
    _SKIP_TYPES = {
        'App::Origin',
        'App::Line',
        'App::Plane',
        'Assembly::JointGroup',
    }

    sel = Gui.Selection.getSelection()
    if sel:
        obj = sel[0]

        # --- Case 1: App::Link pointing to an external document ----------
        if hasattr(obj, "LinkedObject") and obj.LinkedObject is not None:
            linked = obj.LinkedObject
            if hasattr(linked, "Document") and linked.Document != doc:
                rename_mode = "linked"
                target_doc = linked.Document
                parent_doc = doc
                link_obj = obj

        # --- Case 2: Internal object inside the assembly -----------------
        #     (bodies, sub-assemblies, etc. -- but NOT the root assembly
        #      or utility objects like Origin, Joints, etc.)
        if rename_mode == "document" and obj.TypeId not in _SKIP_TYPES:
            # Skip the root assembly -- that falls through to document rename
            if not _is_root_assembly(obj):
                # Verify an assembly exists in this document (we're inside an asm)
                has_assembly = any(
                    o.TypeId == 'Assembly::AssemblyObject' for o in doc.Objects
                )
                if has_assembly:
                    rename_mode = "internal"
                    selected_obj = obj

    # ============================================================
    # GATHER CURRENT NAME / DESCRIPTION BASED ON MODE
    # ============================================================

    if rename_mode == "internal":
        # Internal object -- work with Label and Description property
        base_name = selected_obj.Label
        current_desc = _read_obj_description(selected_obj)
        logical_ext = None  # not applicable
        file_saved = True   # parent doc is used for save context

    elif rename_mode == "linked":
        file_saved = bool(target_doc.FileName)
        if file_saved:
            file_path = str(target_doc.FileName)
            directory = os.path.dirname(file_path)
            filename = os.path.basename(file_path)
            orig_filename = filename

            base_name, _ver, logical_ext, _conforming = _parse_versioned_name(filename)
            if base_name is None:
                QtGui.QMessageBox.warning(
                    None, "Invalid Format",
                    "File must be a FreeCAD file (.FCStd)."
                )
                return
        else:
            base_name = target_doc.Name if target_doc.Name else "Untitled"
            logical_ext = "prt"
            orig_filename = None

        current_desc = _effective_description(target_doc)

    else:  # "document"
        file_saved = bool(doc.FileName)
        target_doc = doc
        if file_saved:
            file_path = str(doc.FileName)
            directory = os.path.dirname(file_path)
            filename = os.path.basename(file_path)
            orig_filename = filename

            base_name, _ver, logical_ext, _conforming = _parse_versioned_name(filename)
            if base_name is None:
                QtGui.QMessageBox.warning(
                    None, "Invalid Format",
                    "File must be a FreeCAD file (.FCStd)."
                )
                return
        else:
            base_name = doc.Name if doc.Name else "Untitled"
            logical_ext = "prt"
            orig_filename = None

        current_desc = _effective_description(doc)

    # ============================================================
    # CREATE PROFESSIONAL DIALOG
    # ============================================================

    dialog = QtGui.QDialog()
    if rename_mode == "internal":
        _is_sub_asm = selected_obj.TypeId == 'Assembly::AssemblyObject'
        dialog.setWindowTitle("Rename Sub Assembly" if _is_sub_asm else "Rename Part")
    elif rename_mode == "linked":
        kind = "Assembly" if logical_ext == "asm" else "Part"
        dialog.setWindowTitle(f"Rename {kind}")
    else:
        dialog.setWindowTitle("Rename Model")
    dialog.setMinimumWidth(450)

    main_layout = QtGui.QVBoxLayout(dialog)
    main_layout.setSpacing(12)

    # ------------------------------
    # MODEL INFORMATION GROUP
    # ------------------------------
    info_group = QtGui.QGroupBox("Model Information")
    info_layout = QtGui.QFormLayout()

    current_name_label = QtGui.QLabel(base_name)
    current_desc_label = QtGui.QLabel(current_desc if current_desc else "-")

    info_layout.addRow("Name:", current_name_label)
    info_layout.addRow("Description:", current_desc_label)

    if rename_mode == "internal":
        _type_text = "Sub Assembly" if selected_obj.TypeId == 'Assembly::AssemblyObject' else selected_obj.TypeId.split("::")[-1]
        type_label = QtGui.QLabel(_type_text)
        info_layout.addRow("Type:", type_label)
        asm_file = os.path.basename(str(doc.FileName)) if doc.FileName else doc.Name
        info_layout.addRow("Parent Assembly:", QtGui.QLabel(asm_file))

    elif rename_mode == "linked":
        kind_label = QtGui.QLabel(logical_ext.upper())
        info_layout.addRow("Type:", kind_label)
        parent_label = QtGui.QLabel(
            os.path.basename(str(parent_doc.FileName)) if parent_doc.FileName else parent_doc.Name
        )
        info_layout.addRow("Parent Assembly:", parent_label)

    info_group.setLayout(info_layout)
    main_layout.addWidget(info_group)

    # ------------------------------
    # EDIT DETAILS GROUP
    # ------------------------------
    edit_group = QtGui.QGroupBox("Edit Details")
    edit_layout = QtGui.QFormLayout()

    name_edit = QtGui.QLineEdit()
    name_edit.setText(base_name)

    desc_edit = QtGui.QLineEdit()
    desc_edit.setText(current_desc)

    edit_layout.addRow("New Name:", name_edit)
    edit_layout.addRow("New Description:", desc_edit)

    edit_group.setLayout(edit_layout)
    main_layout.addWidget(edit_group)

    # ------------------------------
    # BUTTONS
    # ------------------------------
    buttons = QtGui.QDialogButtonBox(
        QtGui.QDialogButtonBox.Ok | QtGui.QDialogButtonBox.Cancel
    )
    main_layout.addWidget(buttons)

    buttons.accepted.connect(dialog.accept)
    buttons.rejected.connect(dialog.reject)

    if dialog.exec_() != QtGui.QDialog.Accepted:
        return

    new_name = name_edit.text().strip()
    new_desc = desc_edit.text().strip()

    # ============================================================
    # VALIDATION
    # ============================================================

    if not re.match(r"^[A-Za-z0-9_]+$", new_name):
        QtGui.QMessageBox.warning(
            None,
            "Invalid Name",
            "Only letters, numbers and underscore allowed."
        )
        return

    # ================================================================
    #   MODE: INTERNAL OBJECT  (Body / Part inside assembly)
    # ================================================================

    if rename_mode == "internal":
        # Check for duplicate label inside the same assembly
        for o in doc.Objects:
            if o != selected_obj and o.Label == new_name:
                QtGui.QMessageBox.warning(
                    None, "Duplicate Name",
                    f"An object named '{new_name}' already exists in this assembly."
                )
                return

        selected_obj.Label = new_name

        # Set or create Description property
        if hasattr(selected_obj, "Description"):
            selected_obj.Description = new_desc
        elif new_desc:
            selected_obj.addProperty(
                "App::PropertyString", "Description", "Base", "Part description"
            )
            selected_obj.Description = new_desc

        # Sync Model Parameters properties
        if hasattr(selected_obj, "MP_PartNumber"):
            selected_obj.MP_PartNumber = new_name
        if hasattr(selected_obj, "MP_Description"):
            selected_obj.MP_Description = new_desc

        doc.recompute()
        doc.save()

        if Gui.ActiveDocument and Gui.ActiveDocument.ActiveView:
            Gui.ActiveDocument.ActiveView.fitAll()

        _success_kind = "Sub Assembly" if selected_obj.TypeId == 'Assembly::AssemblyObject' else "Part"
        QtGui.QMessageBox.information(
            None,
            "Rename Successful",
            f"{_success_kind} Rename Successful!\n\n"
            f"New Name: {new_name}\n"
            f"New Description: {new_desc if new_desc else '-'}"
        )
        # Done -- skip the file-rename logic below
        return

    # ================================================================
    #   MODE: DOCUMENT / LINKED  (file rename on disk)
    # ================================================================

    # ================================================================
    #   NAME UNCHANGED  ->  DESCRIPTION-ONLY UPDATE (no file rename)
    # ================================================================
    # If the user only edited the description (the name is identical to
    # the current one) there is nothing to rename on disk. Skip the whole
    # close / os.rename / XML-patch / strip-Group-prefixes / reopen
    # sequence -- that sequence is only meant for an actual filename
    # change and is destructive for assemblies (it rewrites the Group
    # link values and reopens the document, which was dropping the root
    # Assembly object out of the model tree). Just update the Description
    # in place and report an update -- not a rename.
    if new_name == base_name and file_saved:
        if hasattr(target_doc, "Description"):
            target_doc.Description = new_desc
        apply_info_to_first_body(target_doc, new_name, new_desc)
        if hasattr(target_doc, "MP_PartNumber"):
            target_doc.MP_PartNumber = new_name
        if hasattr(target_doc, "MP_Description"):
            target_doc.MP_Description = new_desc

        target_doc.recompute()
        target_doc.purgeTouched()
        try:
            target_doc.save()
        except Exception:
            pass

        if Gui.ActiveDocument and Gui.ActiveDocument.ActiveView:
            Gui.ActiveDocument.ActiveView.fitAll()

        QtGui.QMessageBox.information(
            None,
            "Details Updated",
            "Description Updated!\n\n"
            f"Name: {new_name} (unchanged)\n"
            f"New Description: {new_desc if new_desc else '-'}"
        )
        return

    # ============================================================
    # HANDLE UNSAVED FILE -- RENAME FIRST, THEN SAVE
    # ============================================================

    if not file_saved:
        directory = QtGui.QFileDialog.getExistingDirectory(
            None, "Select Save Directory", os.path.expanduser("~")
        )
        if not directory:
            return

        new_filename = f"{new_name}.001.FCStd"
        new_full_path = os.path.join(directory, new_filename)

        if os.path.exists(new_full_path):
            QtGui.QMessageBox.warning(
                None,
                "File Exists",
                f"File already exists:\n{new_filename}"
            )
            return

        # Update description before saving
        if hasattr(target_doc, "Description"):
            target_doc.Description = new_desc

        # Apply name & description to first body
        apply_info_to_first_body(target_doc, new_name, new_desc)

        # Sync Model Parameters properties
        if hasattr(target_doc, "MP_PartNumber"):
            target_doc.MP_PartNumber = new_name
        if hasattr(target_doc, "MP_Description"):
            target_doc.MP_Description = new_desc

        target_doc.saveAs(new_full_path)
        target_doc.recompute()
        Gui.ActiveDocument.ActiveView.fitAll()

        QtGui.QMessageBox.information(
            None,
            "Rename Successful",
            f"Rename Successful!\n\n"
            f"New Name: {new_name}\n"
            f"New Description: {new_desc if new_desc else '-'}\n"
            f"Saved to: {new_full_path}"
        )
        return  # Stop here for unsaved files

    # ============================================================
    # FIND ALL VERSIONS (saved file path)
    # Only the LATEST version is renamed to new_name.001.
    # Older versions stay under the old name as archived history.
    # This ensures version numbering restarts from .001 after a rename.
    # ============================================================

    files = os.listdir(directory)
    version_files = []

    for f in files:
        m = re.match(rf"^{re.escape(base_name)}\.(\d{{3}})(?:\.(?:prt|asm|drg))?\.FCStd$", f, re.IGNORECASE)
        if m:
            ver_num = int(m.group(1))
            old_full = os.path.join(directory, f)
            version_files.append((ver_num, old_full))

    # Fallback: the original file did not follow the BaseName.NNN.ext.FCStd
    # convention (e.g. "Flange.005.FCStd" or "Flange.FCStd"), so the strict
    # scan above found nothing. Rename the actual on-disk file directly; it
    # gets normalised to NewName.001.<ext>.FCStd below.
    if not version_files and orig_filename:
        cur_full = os.path.join(directory, orig_filename)
        if os.path.exists(cur_full):
            version_files.append((1, cur_full))

    if not version_files:
        QtGui.QMessageBox.warning(None, "Error", "No version files found.")
        return

    # Sort ascending and take only the latest version
    version_files.sort(key=lambda x: x[0])
    _latest_ver_num, latest_old_path = version_files[-1]

    new_filename_001 = f"{new_name}.001.FCStd"
    new_full_001 = os.path.join(directory, new_filename_001)
    rename_list = [(latest_old_path, new_full_001, "001")]

    # ============================================================
    # CHECK TARGET FILE DOESN'T ALREADY EXIST
    # ============================================================

    for old_path, new_path, ver in rename_list:
        if old_path != new_path and os.path.exists(new_path):
            QtGui.QMessageBox.warning(
                None,
                "File Exists",
                f"Target file already exists:\n{os.path.basename(new_path)}\n\n"
                f"A file with the name '{new_name}' already has a version history."
            )
            return

    # ============================================================
    # UPDATE LINK LABELS IN ALL OPEN REFERENCING ASSEMBLIES
    # Do this BEFORE closing anything — target_doc is still alive so
    # LinkedObject resolution works reliably.
    # ============================================================

    _target_norm = (os.path.normcase(os.path.abspath(str(target_doc.FileName)))
                    if target_doc.FileName else None)

    def _links_to_target(lo_doc):
        """Return True if lo_doc is target_doc (by Name or by FileName)."""
        if lo_doc is None:
            return False
        if lo_doc.Name == target_doc.Name:
            return True
        if _target_norm and lo_doc.FileName:
            return os.path.normcase(os.path.abspath(str(lo_doc.FileName))) == _target_norm
        return False

    def _update_link_labels_in_doc(asm_doc):
        """Rename every App::Link (and embedded object) in asm_doc whose
        label matches base_name and whose LinkedObject lives in target_doc."""
        for obj in asm_doc.Objects:
            # Guard: only touch objects whose label is ALREADY the old name.
            # Without this, any object that happens to link to target_doc
            # (even with a completely different label like "9595") would get
            # incorrectly renamed to new_name.
            if obj.Label != base_name:
                continue
            updated = False
            # Case 1a — LinkedObject property (App::Link style)
            lo = getattr(obj, 'LinkedObject', None)
            if lo is not None and _links_to_target(getattr(lo, 'Document', None)):
                obj.Label = new_name
                updated = True
            # Case 1b — OutList fallback (Assembly::AssemblyLink style)
            if not updated:
                for out_obj in getattr(obj, 'OutList', []):
                    if _links_to_target(getattr(out_obj, 'Document', None)):
                        obj.Label = new_name
                        updated = True
                        break
            # Case 2 — embedded Body or sub-assembly with matching old label
            if (not updated
                    and obj.TypeId in ('PartDesign::Body', 'Assembly::AssemblyObject')
                    and obj.Document.Name == asm_doc.Name):
                obj.Label = new_name

    def _update_gp_link_labels(gp_doc):
        """Update AssemblyLink labels in a grandparent doc.

        Targets AssemblyLinks whose label is still base_name and whose OutList
        contains an item already labeled new_name inside one of the referencing
        docs (the indirect link that _update_link_labels_in_doc cannot reach
        because it only checks direct links to target_doc).
        """
        _ref_norms_set = set()
        for _rn, _rp in referencing_docs_info:
            if _rp:
                _ref_norms_set.add(os.path.normcase(os.path.abspath(_rp)))

        def _is_ref_doc(doc):
            if doc is None or not doc.FileName:
                return False
            return (os.path.normcase(os.path.abspath(str(doc.FileName)))
                    in _ref_norms_set)

        for obj in gp_doc.Objects:
            if obj.Label != base_name:
                continue
            for out_obj in getattr(obj, 'OutList', []):
                if (out_obj.Label == new_name
                        and _is_ref_doc(getattr(out_obj, 'Document', None))):
                    obj.Label = new_name
                    break

    def _fcstd_contains_name(fpath, search_name):
        """Return True if the FCStd zip's Document.xml mentions search_name."""
        try:
            with zipfile.ZipFile(fpath, 'r') as zf:
                if 'Document.xml' not in zf.namelist():
                    return False
                xml = zf.read('Document.xml').decode('utf-8', errors='replace')
                return search_name in xml
        except Exception:
            return False

    def _patch_fcstd_xml(fpath, fname_map):
        """Rewrite ALL xml entries inside the FCStd zip, replacing every key in
        fname_map with its value (bytes-level replacement of filename strings).
        FreeCAD stores XLink references in both Document.xml and GuiDocument.xml,
        so we patch every *.xml file in the archive.
        Works on the file in-place via a temp file + atomic replace.
        Returns True if any replacement was made, False otherwise.
        """
        tmp_path = fpath + '.patch_tmp'
        total_replacements = 0
        try:
            with zipfile.ZipFile(fpath, 'r') as zin:
                with zipfile.ZipFile(tmp_path, 'w',
                                     compression=zipfile.ZIP_DEFLATED) as zout:
                    for item in zin.infolist():
                        data = zin.read(item.filename)
                        # Patch every XML file in the archive
                        if item.filename.lower().endswith('.xml'):
                            for old_fn, new_fn in fname_map.items():
                                old_bytes = old_fn.encode('utf-8')
                                new_bytes = new_fn.encode('utf-8')
                                count = data.count(old_bytes)
                                if count:
                                    data = data.replace(old_bytes, new_bytes)
                                    total_replacements += count
                                    print(f'    [{item.filename}] '
                                          f'{old_fn} -> {new_fn} ({count}x)')
                        zout.writestr(item, data)
            os.replace(tmp_path, fpath)
            return total_replacements > 0
        except Exception as e:
            print(f'  Warning: could not patch XML in {fpath}: {e}')
            if os.path.exists(tmp_path):
                try:
                    os.remove(tmp_path)
                except Exception:
                    pass
            return False

    def _strip_group_link_prefixes(fpath):
        """Remove doc-Name prefixes from Assembly Group link values in the FCStd.

        FreeCAD serialises Assembly::AssemblyObject.Group as cross-doc-qualified
        refs even for intra-document objects:
            <Link value="Unnamed.AssemblyLink"/>
            <Link value="jhkhjk.AssemblyLink"/>
        After any rename/reopen the document receives a NEW internal Name so the
        old prefix no longer resolves and Assembly silently drops those objects
        from the Group.
        This function strips the prefix unconditionally:
            <Link value="Unnamed.AssemblyLink"/> → <Link value="AssemblyLink"/>
        Plain intra-document refs always resolve regardless of what Name FreeCAD
        assigns the document on the next open.
        """
        tmp_path = fpath + '.grp_tmp'
        try:
            changed = False
            with zipfile.ZipFile(fpath, 'r') as zin:
                with zipfile.ZipFile(tmp_path, 'w',
                                     compression=zipfile.ZIP_DEFLATED) as zout:
                    for item in zin.infolist():
                        data = zin.read(item.filename)
                        if item.filename.lower().endswith('.xml'):
                            text = data.decode('utf-8', errors='replace')
                            # Strip "DocName." prefix from every <Link value="..."/>
                            # Pattern:  <Link value="WORD.rest"/>  →  <Link value="rest"/>
                            new_text = re.sub(
                                r'(<Link\s+value=")([A-Za-z0-9_]+)\.',
                                r'\1',
                                text
                            )
                            if new_text != text:
                                changed = True
                                print(f'    [{item.filename}] stripped Group link prefixes')
                                data = new_text.encode('utf-8')
                        zout.writestr(item, data)
            if changed:
                os.replace(tmp_path, fpath)
            else:
                os.remove(tmp_path)
            return changed
        except Exception as exc:
            print(f'  Warning: could not strip Group link prefixes in {fpath}: {exc}')
            if os.path.exists(tmp_path):
                try:
                    os.remove(tmp_path)
                except Exception:
                    pass
            return False

    def _find_referencing_asm_files_on_disk(search_dirs, already_open_paths):
        """Find all closed .asm.FCStd files in search_dirs (list of dirs,
        searched recursively up to 3 levels) that reference the old base_name
        or old filename. Returns list of unique full file paths.
        Does NOT open any files — only checks Document.xml in the zip."""
        found = []
        seen = set()
        asm_pattern = re.compile(r"^.+\.\d{3}(?:\.(?:prt|asm|drg))?\.FCStd$", re.IGNORECASE)
        norm_target = os.path.normcase(os.path.abspath(str(target_doc.FileName)))

        # Build a set of old filenames (all versions) for fast check
        old_fnames = set(os.path.basename(op) for op, _, _ in rename_list)

        def _scan_dir(scan_dir, depth):
            if depth > 3:
                return
            try:
                entries = os.listdir(scan_dir)
            except Exception:
                return
            for fname in sorted(entries):
                fpath = os.path.join(scan_dir, fname)
                if os.path.isdir(fpath):
                    _scan_dir(fpath, depth + 1)
                    continue
                if not asm_pattern.match(fname):
                    continue
                norm_fpath = os.path.normcase(os.path.abspath(fpath))
                if norm_fpath in already_open_paths:
                    continue
                if norm_fpath == norm_target:
                    continue
                if norm_fpath in seen:
                    continue
                # Only check for actual filename references (not base_name —
                # that causes false positives for any file containing the number)
                matched = False
                for ofn in old_fnames:
                    if _fcstd_contains_name(fpath, ofn):
                        matched = True
                        break
                if matched:
                    seen.add(norm_fpath)
                    found.append(fpath)

        if isinstance(search_dirs, str):
            search_dirs = [search_dirs]
        for sd in search_dirs:
            if sd and os.path.isdir(sd):
                _scan_dir(sd, 0)
        return found

    referencing_docs_info = []   # list of (doc_name, file_path) still needed for close/reopen
    target_doc_name = target_doc.Name

    for d in list(App.listDocuments().values()):
        if d == target_doc:
            continue
        has_ref = False
        for obj in d.Objects:
            # Primary: check LinkedObject property (works for App::Link)
            lo = getattr(obj, 'LinkedObject', None)
            if lo is not None:
                if _links_to_target(getattr(lo, 'Document', None)):
                    has_ref = True
                    break
            # Fallback: scan OutList for cross-doc refs
            # Assembly::AssemblyLink may not expose LinkedObject reliably
            if not has_ref:
                for out_obj in getattr(obj, 'OutList', []):
                    if _links_to_target(getattr(out_obj, 'Document', None)):
                        has_ref = True
                        break
            if has_ref:
                break
        if has_ref:
            print(f'  Referencing doc: {os.path.basename(str(d.FileName)) if d.FileName else d.Name}')
            referencing_docs_info.append((d.Name, str(d.FileName)))
            # Recompute FIRST so any auto-sync of labels completes,
            # then set our label override, then save WITHOUT recomputing
            # again (a second recompute would reset the label we just set).
            try:
                d.recompute()
            except Exception:
                pass
            _update_link_labels_in_doc(d)
            d.purgeTouched()
            try:
                d.save()
            except Exception:
                pass

    # Detect grandparent docs (docs that reference a referencing doc) NOW,
    # while XLinks are still intact. After close/reopen the OutList breaks
    # and grandparents can no longer be detected by OutList scan.
    _ref_norms = set()
    for _rn, _rp in referencing_docs_info:
        if _rp:
            _ref_norms.add(os.path.normcase(os.path.abspath(_rp)))
    def _norm_in_ref_norms(doc):
        if doc is None or not doc.FileName:
            return False
        return os.path.normcase(os.path.abspath(str(doc.FileName))) in _ref_norms

    grandparent_docs_info = []  # list of (doc_name, file_path)
    for _gd in list(App.listDocuments().values()):
        if _gd == target_doc:
            continue
        _gd_norm = (os.path.normcase(os.path.abspath(str(_gd.FileName)))
                    if _gd.FileName else None)
        if _gd_norm and _gd_norm in _ref_norms:
            continue  # this doc is itself a referencing doc
        _is_gp = False
        for _obj in _gd.Objects:
            # LinkedObject check (App::Link and some AssemblyLink styles)
            _lo = getattr(_obj, 'LinkedObject', None)
            if _lo is not None and _norm_in_ref_norms(getattr(_lo, 'Document', None)):
                _is_gp = True
                break
            # OutList fallback (Assembly::AssemblyLink cross-doc refs)
            for _out in getattr(_obj, 'OutList', []):
                if _norm_in_ref_norms(getattr(_out, 'Document', None)):
                    _is_gp = True
                    break
            if _is_gp:
                break
        if _is_gp:
            grandparent_docs_info.append((_gd.Name, str(_gd.FileName)))
            print(f'  Grandparent doc: {os.path.basename(str(_gd.FileName)) if _gd.FileName else _gd.Name}')

    # Also update the immediate parent assembly (linked mode)
    parent_file_path = None
    if rename_mode == "linked" and parent_doc:
        try:
            parent_doc.recompute()
        except Exception:
            pass
        _update_link_labels_in_doc(parent_doc)
        parent_doc.purgeTouched()
        try:
            parent_doc.save()
        except Exception:
            pass
        parent_file_path = str(parent_doc.FileName)

    # ============================================================
    # SCAN ALL CLOSED ASSEMBLY FILES ON DISK FOR REFERENCES
    # Pure file-level scan — does NOT open files in FreeCAD.
    # Collects paths for XML patching after disk rename.
    # ============================================================

    already_open = set(
        os.path.normcase(os.path.abspath(str(d.FileName)))
        for d in App.listDocuments().values()
        if d.FileName
    )
    # Build a set of directories to search: renamed file dir + open doc dirs +
    # FreeCAD user macro/working dir. Deduplicate by normcase.
    _search_dirs_set = {}
    def _add_search_dir(d):
        nd = os.path.normcase(os.path.abspath(d))
        _search_dirs_set[nd] = d
    _add_search_dir(directory)
    for _d in App.listDocuments().values():
        if _d.FileName:
            _add_search_dir(os.path.dirname(str(_d.FileName)))
    # Also search FreeCAD working directory (often project root)
    _wdir = os.getcwd()
    if _wdir:
        _add_search_dir(_wdir)
    search_dirs = list(_search_dirs_set.values())
    disk_asm_files = _find_referencing_asm_files_on_disk(search_dirs, already_open)
    if disk_asm_files:
        for fn in disk_asm_files:
            print(f"  Closed assembly references old name: {os.path.basename(fn)}")

    # ============================================================
    # STORE RENAME MAPPING FOR REGEN MACRO
    # Written to a JSON file on disk so ANY FreeCAD instance
    # (even a separate window/process) can read it.
    # ============================================================
    _write_rename_entry(base_name, new_name)

    # ============================================================
    # BUILD FILENAME REPLACEMENT MAP FOR XML PATCHING
    # ============================================================

    new_fn = os.path.basename(new_full_001)
    fname_map = {}
    for _ver_num, old_ver_path in version_files:
        old_fn = os.path.basename(old_ver_path)
        if old_fn != new_fn:
            fname_map[old_fn] = new_fn

    if base_name != new_name:
        fname_map['Label="{}"'.format(base_name)] = 'Label="{}"'.format(new_name)
        fname_map['value="{}"'.format(base_name)] = 'value="{}"'.format(new_name)
        old_internal = re.sub(r'[^A-Za-z0-9]', '_', base_name)
        new_internal = re.sub(r'[^A-Za-z0-9]', '_', new_name)
        if old_internal != new_internal:
            fname_map['value="{}.'.format(old_internal)] = 'value="{}.'.format(new_internal)
    else:
        old_internal = re.sub(r'[^A-Za-z0-9]', '_', base_name)
        new_internal = old_internal

    # FreeCAD's Assembly::AssemblyObject.Group stores link values in the XML as
    # doc-qualified names: value="DocName.ObjName" even for objects in the SAME
    # document.  DocName is whatever doc.Name was at save time — it could be the
    # filename-derived name ("jhkhjk") OR the creation-time name ("Unnamed").
    # After a rename the document gets a NEW internal Name so any
    # value="OldName.Link" ref becomes unresolvable; Assembly then drops those
    # objects from the Group.
    # Fix: strip the old doc-Name prefix unconditionally so refs become plain
    # intra-document refs (value="Link") which always resolve regardless of what
    # name FreeCAD assigns the doc on the next open.
    # NOTE: this intentionally OVERRIDES the earlier value="base_name." entry
    # that would rename the prefix (jhkhjk.→321.) — renaming is wrong because
    # FreeCAD derives a completely different internal Name from the new filename.
    if target_doc_name:
        fname_map['value="{}.'.format(target_doc_name)] = 'value="'

    print(f"  fname_map: {fname_map}")

    # ============================================================
    # PERFORM RENAME
    # ============================================================
    #
    # "document" mode — close only the ROOT, keep sub-docs open.
    #   Patch XML to strip old doc-Name prefix from Group link values.
    #   Reopen root — sub-docs already in registry so XLinks resolve.
    #
    # "linked" mode — close target, rename on disk, XML-patch referencing
    #   files, then reopen.
    # ============================================================

    if rename_mode == "document":

        # Collect referenced sub-docs in leaves-first order so we can save them
        # and, if FreeCAD auto-closes any, reopen them in the right sequence.
        def _collect_post_order(doc, visited, result):
            if doc.Name in visited:
                return
            visited.add(doc.Name)
            for obj in doc.Objects:
                lo = getattr(obj, 'LinkedObject', None)
                if lo is None:
                    continue
                lo_doc = getattr(lo, 'Document', None)
                if lo_doc is not None:
                    _collect_post_order(lo_doc, visited, result)
            if doc.Name != target_doc_name and doc.FileName:
                result.append((doc.Name, str(doc.FileName)))

        ref_ordered = []   # [(doc_name, file_path)] leaves-first
        _collect_post_order(target_doc, set(), ref_ordered)

        # Save every referenced sub-doc WITHOUT closing it.
        # Sub-docs must remain open so their entries stay in FreeCAD's XLink
        # registry — the root reads that registry on open to resolve its
        # Assembly::AssemblyLink → sub-assembly cross-document links.
        for dname, _dpath in ref_ordered:
            d = App.getDocument(dname)
            if d and d.FileName:
                try:
                    d.save()
                except Exception:
                    pass

        # Save the root document to disk, then close it.
        # Saving now commits all AssemblyLink objects (added since last save)
        # into the file before we rename it.
        old_file_path = str(target_doc.FileName)
        try:
            target_doc.save()
        except Exception as _exc:
            print(f'  Warning: pre-rename root save failed: {_exc}')
        App.closeDocument(target_doc_name)
        # Sub-docs are still open at this point.

        # Rename the file on disk.
        try:
            os.rename(old_file_path, new_full_001)
        except Exception as exc:
            QtGui.QMessageBox.critical(None, "Rename Failed",
                f"Failed to rename file on disk:\n{str(exc)}")
            return

        # ---- CRITICAL XML PATCH ----
        # 1. String replacements: rename Label/value/filename references.
        if fname_map and os.path.exists(new_full_001):
            _patch_fcstd_xml(new_full_001, fname_map)

        # 2. Regex strip: remove ALL doc-Name prefixes from Group link values.
        #    FreeCAD serialises Assembly::AssemblyObject.Group as qualified refs
        #    value="DocName.ObjName" even for objects in the SAME document.
        #    The DocName at save time could be "Unnamed", "33265", or anything
        #    else — we cannot know it reliably via fname_map string matching.
        #    The regex strips any "Word." prefix, converting qualified refs to
        #    plain intra-doc refs that resolve regardless of the new doc Name.
        if os.path.exists(new_full_001):
            _strip_group_link_prefixes(new_full_001)

        # Patch any referencing docs on disk (rare for a root rename)
        if fname_map and referencing_docs_info:
            seen_p = set()
            for _rn, ref_doc_path in referencing_docs_info:
                if not ref_doc_path or not os.path.exists(ref_doc_path):
                    continue
                norm = os.path.normcase(os.path.abspath(ref_doc_path))
                if norm in seen_p:
                    continue
                seen_p.add(norm)
                print(f'  Patching referencing doc: {os.path.basename(ref_doc_path)}')
                _patch_fcstd_xml(ref_doc_path, fname_map)

        # Patch any closed assembly files found on disk
        if fname_map and disk_asm_files:
            seen_p = set()
            for fpath in disk_asm_files:
                norm = os.path.normcase(os.path.abspath(fpath))
                if norm in seen_p or not os.path.exists(fpath):
                    continue
                seen_p.add(norm)
                _patch_fcstd_xml(fpath, fname_map)

        # If FreeCAD auto-closed any sub-docs when the root was closed, reopen
        # them now in leaves-first order so every XLink target is in the
        # registry before the doc that references it is loaded.
        for _dname, dpath in ref_ordered:
            norm = os.path.normcase(os.path.abspath(dpath))
            already = any(
                os.path.normcase(os.path.abspath(str(d.FileName))) == norm
                for d in App.listDocuments().values() if d.FileName
            )
            if not already and os.path.exists(dpath):
                try:
                    App.openDocument(dpath)
                except Exception:
                    pass

        # Open the renamed root — sub-docs are in the registry, and the patched
        # XML now uses plain intra-doc refs (value="ObjName") so the Group
        # resolves correctly regardless of the new internal doc Name.
        new_doc = App.openDocument(new_full_001)

        # Post-rename sweep: fix any link labels in open parent docs that still
        # show the old name. Recompute FIRST so auto-sync completes, then
        # override the label, then save WITHOUT another recompute (a second
        # recompute would reset the label back to the old value).
        # Guard: only change labels that equal base_name to avoid accidentally
        # renaming unrelated links (e.g. a "9595" link inside the renamed assembly).
        for _pd in list(App.listDocuments().values()):
            if _pd.Name == new_doc.Name:
                continue
            try:
                _pd.recompute()
            except Exception:
                pass
            _fixed = False
            for _obj in _pd.Objects:
                if _obj.Label != base_name:
                    continue  # only update links that carry the old name
                _lo = getattr(_obj, 'LinkedObject', None)
                if _lo is not None:
                    _lo_doc = getattr(_lo, 'Document', None)
                    if _lo_doc is not None and _lo_doc.Name == new_doc.Name:
                        _obj.Label = new_name
                        _fixed = True
                        continue
                for _out in getattr(_obj, 'OutList', []):
                    if getattr(_out, 'Document', None) is not None:
                        if _out.Document.Name == new_doc.Name:
                            _obj.Label = new_name
                            _fixed = True
                            break
            if _fixed and _pd.FileName:
                try:
                    _pd.purgeTouched()
                    _pd.save()
                except Exception:
                    pass

        if hasattr(new_doc, "Description"):
            new_doc.Description = new_desc
        apply_info_to_first_body(new_doc, new_name, new_desc)
        if hasattr(new_doc, "MP_PartNumber"):
            new_doc.MP_PartNumber = new_name
        if hasattr(new_doc, "MP_Description"):
            new_doc.MP_Description = new_desc
        new_doc.recompute()
        new_doc.purgeTouched()
        new_doc.save()

        # Step 1: Save grandparents and strip their Group prefixes BEFORE closing
        # referencing docs. XLinks are still intact at this point, so the saved
        # file captures the complete Group content (AssemblyLink included).
        # Stripping replaces value="DocName.Link" with value="Link" so the Group
        # resolves correctly regardless of what Name FreeCAD assigns on reopen.
        for _gd_name, _gd_path in grandparent_docs_info:
            _gd = App.getDocument(_gd_name)
            if _gd is None or not _gd_path:
                continue
            try:
                _gd.save()
            except Exception:
                pass
            _strip_group_link_prefixes(_gd_path)

        # Step 2: Reload referencing docs (parent assemblies).
        # Strip their Group prefixes too so intra-doc refs survive the Name change.
        for ref_doc_name, ref_doc_path in referencing_docs_info:
            if not ref_doc_path or not os.path.exists(ref_doc_path):
                continue
            _strip_group_link_prefixes(ref_doc_path)
            try:
                stale = App.getDocument(ref_doc_name)
                if stale:
                    App.closeDocument(ref_doc_name)
            except Exception:
                pass
            try:
                rd = App.openDocument(ref_doc_path)
                if rd:
                    rd.recompute()
                    _update_link_labels_in_doc(rd)
                    rd.purgeTouched()
                    rd.save()
                    for _dbg in rd.Objects:
                        if _dbg.TypeId == 'Assembly::AssemblyLink':
                            _dbg_out_doc = next((getattr(o, 'Document', None)
                                                 for o in getattr(_dbg, 'OutList', [])), None)
                            print(f'    [ref reload] {_dbg.Label}'
                                  f' -> {getattr(_dbg_out_doc, "Name", "?")}')
            except Exception:
                pass

        # Step 3: Reload grandparent docs now that referencing docs are open.
        # FreeCAD resolves the grandparent's XLink by filename so it connects
        # to the freshly loaded referencing doc and shows the updated labels.
        for _gd_name, _gd_path in grandparent_docs_info:
            if not _gd_path or not os.path.exists(_gd_path):
                continue
            print(f'  Reloading grandparent: {os.path.basename(_gd_path)}')
            try:
                stale_gd = App.getDocument(_gd_name)
                if stale_gd:
                    App.closeDocument(_gd_name)
            except Exception:
                pass
            try:
                gd_reopened = App.openDocument(_gd_path)
                if gd_reopened:
                    gd_reopened.recompute()
                    _update_gp_link_labels(gd_reopened)
                    gd_reopened.purgeTouched()
                    gd_reopened.save()
                    for _dbg in gd_reopened.Objects:
                        if _dbg.TypeId == 'Assembly::AssemblyLink':
                            for _dbg_out in getattr(_dbg, 'OutList', []):
                                _dbg_out_doc = getattr(_dbg_out, 'Document', None)
                                print(f'    [gp reload] {_dbg.Label}'
                                      f' -> {_dbg_out.Label}'
                                      f' in {getattr(_dbg_out_doc, "Name", "?")}')
            except Exception:
                pass

        active = App.ActiveDocument
        if active:
            active.recompute()
            if Gui.ActiveDocument and Gui.ActiveDocument.ActiveView:
                Gui.ActiveDocument.ActiveView.fitAll()

        QtGui.QMessageBox.information(
            None,
            "Rename Successful",
            f"Rename Successful!\n\n"
            f"New Name: {new_name}\n"
            f"New Description: {new_desc if new_desc else '-'}"
        )
        return

    # ================================================================
    # "LINKED" MODE: close target → rename on disk → XML-patch → reopen
    # ================================================================

    for ref_doc_name, _ref_doc_path in referencing_docs_info:
        try:
            App.closeDocument(ref_doc_name)
        except Exception:
            pass

    App.closeDocument(target_doc_name)

    for old_path, new_path, ver in rename_list:
        if old_path != new_path:
            os.rename(old_path, new_path)

    if fname_map:
        asm_files_to_patch = []
        for _ref_doc_name, ref_doc_path in referencing_docs_info:
            if ref_doc_path and os.path.exists(ref_doc_path):
                asm_files_to_patch.append(ref_doc_path)
        for fpath in disk_asm_files:
            if os.path.exists(fpath):
                asm_files_to_patch.append(fpath)
        if parent_file_path and os.path.exists(parent_file_path):
            asm_files_to_patch.append(parent_file_path)

        seen_patch = set()
        for asm_path in asm_files_to_patch:
            norm = os.path.normcase(os.path.abspath(asm_path))
            if norm in seen_patch:
                continue
            seen_patch.add(norm)
            print(f'  Patching: {os.path.basename(asm_path)}')
            patched = _patch_fcstd_xml(asm_path, fname_map)
            if patched:
                print(f'  XML references patched: {os.path.basename(asm_path)}')
            else:
                print(f'  XML patch: no matching references found in {os.path.basename(asm_path)}')

    rename_list.sort(key=lambda x: x[1])
    latest_file = rename_list[-1][1]

    # Strip doc-name prefixes from Group link values in the renamed file.
    # Assembly::AssemblyObject.Group stores value="DocName.ObjName" even for
    # intra-doc objects; after rename the doc gets a new Name so old prefix
    # is unresolvable. Strip it so refs become plain intra-doc refs.
    if os.path.exists(latest_file):
        _strip_group_link_prefixes(latest_file)

    new_doc = App.openDocument(latest_file)
    new_doc.recompute()

    # Post-rename sweep: fix link labels in any open parent docs still showing old name.
    # Recompute first so auto-sync finishes, then override label, then save
    # WITHOUT another recompute (which would reset the label we just set).
    # Guard: only change labels that equal base_name to avoid accidentally
    # renaming unrelated links (e.g. a "9595" link inside the renamed assembly).
    for _pd in list(App.listDocuments().values()):
        if _pd.Name == new_doc.Name:
            continue
        try:
            _pd.recompute()
        except Exception:
            pass
        _fixed = False
        for _obj in _pd.Objects:
            if _obj.Label != base_name:
                continue  # only update links that carry the old name
            _lo = getattr(_obj, 'LinkedObject', None)
            if _lo is not None:
                _lo_doc = getattr(_lo, 'Document', None)
                if _lo_doc is not None and _lo_doc.Name == new_doc.Name:
                    _obj.Label = new_name
                    _fixed = True
                    continue
            for _out in getattr(_obj, 'OutList', []):
                if getattr(_out, 'Document', None) is not None:
                    if _out.Document.Name == new_doc.Name:
                        _obj.Label = new_name
                        _fixed = True
                        break
        if _fixed and _pd.FileName:
            try:
                _pd.purgeTouched()
                _pd.save()
            except Exception:
                pass

    if hasattr(new_doc, "Description"):
        new_doc.Description = new_desc
    apply_info_to_first_body(new_doc, new_name, new_desc)
    if hasattr(new_doc, "MP_PartNumber"):
        new_doc.MP_PartNumber = new_name
    if hasattr(new_doc, "MP_Description"):
        new_doc.MP_Description = new_desc

    new_doc.recompute()
    new_doc.purgeTouched()
    new_doc.save()

    # Step 1: Save grandparents and strip Group prefixes BEFORE reopening referencing docs.
    for _gd_name, _gd_path in grandparent_docs_info:
        _gd_doc = App.getDocument(_gd_name)
        if _gd_doc is None or not _gd_path:
            continue
        try:
            _gd_doc.save()
        except Exception:
            pass
        _strip_group_link_prefixes(_gd_path)

    # Step 2: Reopen referencing docs (strip Group prefixes first).
    for ref_doc_name, ref_doc_path in referencing_docs_info:
        if ref_doc_path and os.path.exists(ref_doc_path):
            _strip_group_link_prefixes(ref_doc_path)
            try:
                ref_reopened = App.openDocument(ref_doc_path)
                if ref_reopened:
                    ref_reopened.recompute()
                    ref_reopened.purgeTouched()
                    ref_reopened.save()
            except Exception:
                pass

    # Step 3: Reload grandparent docs now that referencing docs are open.
    for _gd_name, _gd_path in grandparent_docs_info:
        if not _gd_path or not os.path.exists(_gd_path):
            continue
        print(f'  Reloading grandparent: {os.path.basename(_gd_path)}')
        try:
            stale_gd = App.getDocument(_gd_name)
            if stale_gd:
                App.closeDocument(_gd_name)
        except Exception:
            pass
        try:
            gd_reopened = App.openDocument(_gd_path)
            if gd_reopened:
                gd_reopened.recompute()
                _update_gp_link_labels(gd_reopened)
                gd_reopened.purgeTouched()
                gd_reopened.save()
        except Exception:
            pass

    if parent_file_path and os.path.exists(parent_file_path):
        parent_already_open = False
        for d in App.listDocuments().values():
            if str(d.FileName) == parent_file_path:
                d.recompute()
                d.purgeTouched()
                d.save()
                App.setActiveDocument(d.Name)
                parent_already_open = True
                break
        if not parent_already_open:
            parent_reopened = App.openDocument(parent_file_path)
            if parent_reopened:
                parent_reopened.recompute()
                parent_reopened.purgeTouched()
                parent_reopened.save()
            App.setActiveDocument(parent_reopened.Name)

    active = App.ActiveDocument
    if active:
        active.recompute()
        if Gui.ActiveDocument and Gui.ActiveDocument.ActiveView:
            Gui.ActiveDocument.ActiveView.fitAll()

    kind = "Assembly" if logical_ext == "asm" else "Part"
    QtGui.QMessageBox.information(
        None,
        "Rename Successful",
        f"{kind} Rename Successful!\n\n"
        f"New Name: {new_name}\n"
        f"New Description: {new_desc if new_desc else '-'}\n"
        f"Files renamed: {len(rename_list)}"
    )


main()
