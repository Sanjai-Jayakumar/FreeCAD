# -*- coding: utf-8 -*-
# BalloonAssembly.FCMacro — BNC CAD  v4
#
# HOW TO USE:
#   1. Run AssemblyTable macro first (establishes S.No order)
#   2. On the TechDraw sheet, click one or more 3D views
#      (hold Ctrl to select multiple views)
#   3. Run this macro
#
#   SPREAD assembly (exploded view): bubbles are placed outward from each
#   part's projected 3D centre — arrow tip lands on the part.
#
#   TIGHT assembly (all parts close together): bubbles are laid out in a
#   numbered column beside the view. Drag each bubble onto its part.
#
#   Re-run to regenerate.  Drag bubbles to fine-tune positions.

import FreeCAD as App
import FreeCADGui as Gui
import re as _re
import math
from FreeCAD import Units as _U
from PySide import QtWidgets

BALLOON_PREFIX = 'BNCBalloon_'

# Perimeter ring: bubbles sit on a ring this far beyond the furthest part
PERIM_MARGIN     = 25.0   # mm added beyond the furthest projected part
PERIM_RADIUS_MIN = 45.0   # mm minimum ring radius from view centre

# Minimum spacing between bubble centres (repulsion)
MIN_BUBBLE_SEP = 11.0

# If parts barely spread at all (single part / degenerate), fall back to
# a numbered column beside the view.
SPREAD_THRESHOLD = 3.0

def _mm(v):
    """Return a FreeCAD Length Quantity from a plain mm float."""
    return _U.Quantity(float(v), _U.Length)

# ============================================================
# SKIP / CONTAINER SETS  (identical to AssemblyTable)
# ============================================================
_SKIP = frozenset({
    'TechDraw::DrawPage','TechDraw::DrawTemplate',
    'TechDraw::DrawViewPart','TechDraw::DrawViewSection',
    'TechDraw::DrawViewDetail','TechDraw::DrawProjGroup',
    'TechDraw::DrawProjGroupItem','TechDraw::DrawViewDimension',
    'TechDraw::DrawViewAnnotation','TechDraw::DrawViewSymbol',
    'TechDraw::DrawViewSpreadsheet','TechDraw::DrawHatch',
    'TechDraw::DrawGeomHatch','TechDraw::DrawViewBalloon',
    'Spreadsheet::Sheet',
    'App::Origin','App::Line','App::Plane',
    'PartDesign::CoordinateSystem','PartDesign::Point',
    'PartDesign::Line','PartDesign::Plane',
    'Sketcher::SketchObject',
})
_CONTAINERS = frozenset({'Assembly::AssemblyObject','App::Part','App::DocumentObjectGroup'})
_PARTS      = frozenset({'PartDesign::Body','Part::Feature','Part::FeaturePython','Part::Compound'})
_SKIP_LBL   = frozenset({'Origin','X_Axis','Y_Axis','Z_Axis',
                          'XY_Plane','XZ_Plane','YZ_Plane','LCS_Origin'})
_GENERIC    = _re.compile(r'^Body\d*$|^Part\d*$|^Sketch\d*$', _re.IGNORECASE)

# ============================================================
# ASSEMBLY HELPERS  (identical to AssemblyTable)
# ============================================================
def _clean(label):
    s = str(label or '').strip()
    s = _re.sub(r'\.(prt|asm|stp|step|iges|igs|FCStd)$', '', s, flags=_re.IGNORECASE)
    s = _re.sub(r'\.\d{3}$', '', s)
    return s.strip() or str(label).strip()

def _desc(obj):
    return str(getattr(obj, 'Label2', '') or '').strip()

def _link_label(obj, linked):
    """Best-effort part name for an App::Link. Assembly links commonly keep
    FreeCAD's default object name ("Body", "Body001", ...) while the real
    part identity lives on the linked EXTERNAL document itself (e.g.
    "Box_CAP.003"). Fall back to that when the link's own label is generic."""
    label = _clean(obj.Label)
    if linked is not None and _GENERIC.match(label):
        try:
            doc_label = _clean(linked.Document.Label)
        except Exception:
            doc_label = ''
        if doc_label and doc_label not in _SKIP_LBL and not _GENERIC.match(doc_label):
            label = doc_label
    return label

def _add(lst, pn, desc=''):
    if not pn or pn in _SKIP_LBL or _GENERIC.match(pn):
        return
    for r in lst:
        if r[0] == pn:
            r[2] += 1
            return
    lst.append([pn, desc, 1])

def _merge(rows):
    merged = []
    for pn, desc, qty in rows:
        m = _re.match(r'^(.+?)(\d{3})$', pn)
        if m:
            base = m.group(1)
            for ex in merged:
                if ex[0] == base:
                    ex[2] += qty
                    break
            else:
                merged.append([pn, desc, qty])
        else:
            merged.append([pn, desc, qty])
    return merged

def _walk(objects, rows, depth=0):
    if depth > 12:
        return
    for obj in objects:
        if obj is None: continue
        tid = obj.TypeId
        if tid in _SKIP or 'TechDraw' in tid: continue
        if obj.Label in _SKIP_LBL: continue
        if tid == 'App::Link':
            linked = getattr(obj, 'LinkedObject', None)
            if linked and linked.TypeId in _CONTAINERS:
                _walk(getattr(linked, 'Group', []), rows, depth + 1)
            else:
                desc = _desc(obj) or (_desc(linked) if linked is not None else '')
                _add(rows, _link_label(obj, linked), desc)
        elif tid in _CONTAINERS:
            children = getattr(obj, 'Group', [])
            handled = False
            if tid == 'App::Part':
                leaf_parts = [c for c in children if c is not None and c.TypeId in _PARTS]
                label = _clean(obj.Label)
                if leaf_parts and label and label not in _SKIP_LBL and not _GENERIC.match(label):
                    # A Part directly wrapping Body/Feature children is the
                    # common "one part = one App::Part" pattern. Its Body
                    # children usually keep FreeCAD's default generic names,
                    # so use the Part's own (meaningful) label for the BOM
                    # row instead of the generic child label.
                    _add(rows, label, _desc(leaf_parts[0]))
                    rest = [c for c in children if c not in leaf_parts]
                    _walk(rest, rows, depth + 1)
                    handled = True
            if not handled:
                _walk(children, rows, depth + 1)
        elif tid in _PARTS:
            _add(rows, _clean(obj.Label), _desc(obj))
        else:
            grp = getattr(obj, 'Group', None)
            if grp:
                _walk(grp, rows, depth + 1)

def get_rows(doc):
    rows = []
    for obj in doc.Objects:
        if obj.TypeId == 'Assembly::AssemblyObject':
            _walk(getattr(obj, 'Group', []), rows)
            break
    if not rows:
        for obj in doc.Objects:
            if obj.TypeId == 'App::Part':
                # Walk the Part itself (not its unwrapped children) so the
                # container-label fallback in _walk() can apply.
                _walk([obj], rows)
    if not rows:
        for obj in doc.Objects:
            if obj.TypeId in _SKIP or 'TechDraw' in obj.TypeId: continue
            if obj.Label in _SKIP_LBL: continue
            parent_tids = {p.TypeId for p in getattr(obj, 'InList', [])}
            if parent_tids & (_PARTS | _CONTAINERS): continue
            if obj.TypeId in _PARTS:
                _add(rows, _clean(obj.Label), _desc(obj))
            elif obj.TypeId == 'App::Link':
                linked = getattr(obj, 'LinkedObject', None)
                if linked and linked.TypeId in _CONTAINERS:
                    _walk(getattr(linked, 'Group', []), rows)
                else:
                    desc = _desc(obj) or (_desc(linked) if linked is not None else '')
                    _add(rows, _link_label(obj, linked), desc)
    if not rows:
        for d in App.listDocuments().values():
            if d is doc: continue
            for obj in d.Objects:
                if obj.TypeId not in _PARTS: continue
                parent_tids = {p.TypeId for p in getattr(obj, 'InList', [])}
                if not (parent_tids & _PARTS):
                    _add(rows, _clean(obj.Label), _desc(obj))
    return _merge(rows)

# ============================================================
# PROJECTION HELPERS
# ============================================================
_VIEW_TYPES = frozenset({
    'TechDraw::DrawViewPart',
    'TechDraw::DrawProjGroupItem',
})

def _plc(obj):
    """Own local placement of an object (identity if none)."""
    p = getattr(obj, 'Placement', None)
    return p if p is not None else App.Placement()

def collect_instances(objects, parent_plc, out, depth=0, exp_plc=None):
    """
    Walk the assembly tree collecting PLACED part instances with their
    WORLD bounding-box centres.  This is the crucial difference from
    reading source .prt geometry (which sits at each part's own origin,
    causing every balloon to collapse onto one point).

    parent_plc holds the accumulated placement of ANCESTORS only.  An
    object's own Placement is already baked into its Shape.BoundBox, so we
    transform the shape's bbox centre by parent_plc — never double-count.

    exp_plc (optional) maps {part_obj: exploded_placement}; when given, a
    part's geometry is moved to its exploded position so balloon tips match
    an exploded view.

    out receives (clean_label, world_centre_Vector) tuples.
    """
    if depth > 12:
        return
    for obj in objects:
        if obj is None:
            continue
        tid = obj.TypeId
        if tid in _SKIP or 'TechDraw' in tid:
            continue
        if obj.Label in _SKIP_LBL:
            continue

        if tid == 'App::Link':
            linked = getattr(obj, 'LinkedObject', None)
            if linked is not None and linked.TypeId in _CONTAINERS:
                # Link points at a sub-assembly: descend, adding the link's
                # placement and the linked container's own placement.
                child_plc = parent_plc.multiply(_plc(obj)).multiply(_plc(linked))
                collect_instances(getattr(linked, 'Group', []), child_plc, out, depth + 1, exp_plc)
            else:
                g = _leaf_geom(obj, parent_plc, exp_plc)
                if g is not None:
                    out.append((_link_label(obj, linked), g[0], g[1]))
        elif tid in _CONTAINERS:
            child_plc = parent_plc.multiply(_plc(obj))
            children = getattr(obj, 'Group', [])
            handled = False
            if tid == 'App::Part':
                leaf_parts = [c for c in children if c is not None and c.TypeId in _PARTS]
                label = _clean(obj.Label)
                if leaf_parts and label and label not in _SKIP_LBL and not _GENERIC.match(label):
                    # Mirror _walk()'s container-label fallback so each leaf
                    # Body's geometry is filed under the SAME name its BOM
                    # row uses, even though the Body itself is unnamed.
                    for lp in leaf_parts:
                        g = _leaf_geom(lp, child_plc, exp_plc)
                        if g is not None:
                            out.append((label, g[0], g[1]))
                    rest = [c for c in children if c not in leaf_parts]
                    collect_instances(rest, child_plc, out, depth + 1, exp_plc)
                    handled = True
            if not handled:
                collect_instances(children, child_plc, out, depth + 1, exp_plc)
        elif tid in _PARTS:
            g = _leaf_geom(obj, parent_plc, exp_plc)
            if g is not None:
                out.append((_clean(obj.Label), g[0], g[1]))
        else:
            grp = getattr(obj, 'Group', None)
            if grp:
                collect_instances(grp, parent_plc.multiply(_plc(obj)), out, depth + 1, exp_plc)

def _bbox_corners(bb):
    """The 8 corner points of an (axis-aligned) BoundBox."""
    from FreeCAD import Vector
    return [Vector(x, y, z)
            for x in (bb.XMin, bb.XMax)
            for y in (bb.YMin, bb.YMax)
            for z in (bb.ZMin, bb.ZMax)]

def _shape_bbox(obj, depth=0):
    """Return a valid LOCAL BoundBox for obj, even if obj itself has no
    Shape — aggregates children's shapes recursively (e.g. a Link or
    container whose own Shape is empty but whose children carry the real
    geometry, as happens with some fastener/standard-part objects). This
    is what keeps a single unresolved part from collapsing to a point and
    corrupting the whole assembly's measured extent (which then feeds the
    exploded-view tip-scale correction and skews EVERY balloon, not just
    the one part that failed)."""
    if depth > 8 or obj is None:
        return None
    shp = getattr(obj, 'Shape', None)
    if shp is not None and getattr(shp, 'BoundBox', None) is not None:
        try:
            if shp.BoundBox.isValid():
                return shp.BoundBox
        except Exception:
            pass
    bb = None
    for child in getattr(obj, 'Group', []) or []:
        cbb = _shape_bbox(child, depth + 1)
        if cbb is None:
            continue
        if bb is None:
            bb = App.BoundBox(cbb.XMin, cbb.YMin, cbb.ZMin, cbb.XMax, cbb.YMax, cbb.ZMax)
        else:
            bb.add(cbb)
    return bb


def _exploded_delta(obj, exp_plc):
    """World-to-world transform that moves obj from its assembled placement to
    its EXPLODED placement, or None if obj isn't part of the explode.
    exp_plc = {part_obj: exploded_App.Placement} (read-only from ExplodedView)."""
    if not exp_plc:
        return None
    final = exp_plc.get(obj)
    if final is None:
        return None
    try:
        return final.multiply(_plc(obj).inverse())
    except Exception:
        return None


def _leaf_geom(obj, parent_plc, exp_plc=None):
    """
    Return (world_centre, [8 world corner points]) for a placed leaf part.
    Robust to how the object exposes geometry — parts here are App::Links
    to EXTERNAL part documents, so obj.Shape is often absent.

    If exp_plc is given and obj is in it, the returned world geometry is moved
    to the part's EXPLODED position — so balloon tips land on the parts where
    they are actually drawn in an exploded view (stacked parts separate out).
    """
    gplc = None
    try:
        gplc = obj.getGlobalPlacement()
    except Exception:
        gplc = None

    centre = None
    corners = None

    # A) direct Shape (or aggregated children) — bbox already in the parent frame
    bb = _shape_bbox(obj)
    if bb is not None:
        corners = [parent_plc.multVec(c) for c in _bbox_corners(bb)]
        centre = parent_plc.multVec(bb.Center)
    else:
        # B) App::Link to an external-document part: linked local bbox, placed
        linked = getattr(obj, 'LinkedObject', None)
        if linked is not None:
            lbb = _shape_bbox(linked)
            if lbb is not None:
                plc = gplc if gplc is not None else parent_plc.multiply(_plc(obj))
                corners = [plc.multVec(c) for c in _bbox_corners(lbb)]
                centre = plc.multVec(lbb.Center)

    if centre is None:
        # C) last resort: the part's world origin (zero-size box)
        App.Console.PrintWarning(
            'BalloonAssembly: could not resolve real geometry for {} — '
            'its balloon tip will collapse to a point.\n'.format(obj.Label))
        base = gplc.Base if gplc is not None else parent_plc.multiply(_plc(obj)).Base
        centre, corners = base, [base]

    # Move to exploded position if this part is exploded (tips follow the drawn parts)
    delta = _exploded_delta(obj, exp_plc)
    if delta is not None:
        centre = delta.multVec(centre)
        corners = [delta.multVec(c) for c in corners]

    return centre, corners

def get_instances(doc, exp_plc=None):
    """Return {clean_label: [(world_centre, corners), ...]} for all parts.
    If exp_plc is given, parts are placed at their EXPLODED positions."""
    out = []
    for obj in doc.Objects:
        if obj.TypeId == 'Assembly::AssemblyObject':
            collect_instances(getattr(obj, 'Group', []), App.Placement(), out, 0, exp_plc)
            break
    if not out:
        for obj in doc.Objects:
            if obj.TypeId == 'App::Part':
                collect_instances(getattr(obj, 'Group', []), App.Placement(), out, 0, exp_plc)
    name_map = {}
    for label, centre, corners in out:
        name_map.setdefault(label, []).append((centre, corners))
    return name_map


def _exploded_placements(doc):
    """READ-ONLY: {part_obj: exploded_App.Placement} from every ExplodedView in
    the doc.  Calls the Assembly ExplodedView proxy's calculation which returns
    placements WITHOUT applying them — the exploded view and document are left
    completely unchanged."""
    result = {}
    for o in doc.Objects:
        proxy = getattr(o, 'Proxy', None)
        if proxy is not None and hasattr(proxy, '_calculateExplodedPlacements'):
            try:
                fp, _lines = proxy._calculateExplodedPlacements(o)
                if fp:
                    result.update(fp)
            except Exception as e:
                App.Console.PrintWarning(
                    '[BalloonAssembly] could not read exploded placements from '
                    '{}: {}\n'.format(getattr(o, 'Name', '?'), e))
    return result


def _view_sources_exploded(view):
    """True if this TechDraw view is a projection of an exploded view."""
    for s in getattr(view, 'Source', []) or []:
        proxy = getattr(s, 'Proxy', None)
        if proxy is not None and hasattr(proxy, '_calculateExplodedPlacements'):
            return True
        if 'Exploded' in getattr(s, 'Name', '') or 'Exploded' in getattr(s, 'Label', ''):
            return True
    return False

def match_all_geom(part_name, name_map):
    """Find ALL (world_centre, corners) instances for a table row name
    (exact, then 001/suffix). A BOM row with Qty > 1 (e.g. 8 identical
    bolts) has one entry per physical instance here — every one of them
    gets its own balloon, not just the first."""
    if part_name in name_map:
        return name_map[part_name]
    if part_name + '001' in name_map:
        return name_map[part_name + '001']
    for lbl, entries in name_map.items():
        if lbl.startswith(part_name) and lbl[len(part_name):].isdigit():
            return entries
    return []

def _view_scale(view):
    try:
        if view.TypeId == 'TechDraw::DrawProjGroupItem':
            grp = next((o for o in getattr(view, 'InList', [])
                        if o.TypeId == 'TechDraw::DrawProjGroup'), None)
            if grp:
                return float(grp.Scale)
        return float(view.Scale)
    except Exception:
        return 1.0

def _view_axes(view):
    """View-local 2D basis. Direction is the projection direction (into the
    screen, away from the viewer); XDirection is the view's screen-right.
    Screen-up must be Direction x XDirection — e.g. for the standard Front
    view (Direction=(0,-1,0), XDirection=(1,0,0)) that gives (0,0,1), i.e.
    world +Z, matching FreeCAD's own convention. The reverse cross-product
    order silently flips every view's up axis (top/bottom swapped)."""
    from FreeCAD import Vector
    xd = Vector(view.XDirection).normalize()
    d  = Vector(view.Direction).normalize()
    yd = d.cross(xd).normalize()
    return xd, yd

def _view_extent_2d(view):
    """
    Radius (mm) enclosing the ACTUAL drawn geometry of the view, measured
    from the view centre.  Read straight from TechDraw's projected 2D
    geometry so it is correct for EXPLODED views too (where the drawn parts
    are far more spread out than the assembled 3D placements).
    Returns (radius, half_width, half_height) or None if unavailable.
    """
    candidates = []
    # DrawViewPart may expose the projected compound as .Shape
    shp = getattr(view, 'Shape', None)
    if shp is not None and getattr(shp, 'BoundBox', None) is not None:
        try:
            if shp.BoundBox.isValid():
                candidates.append(shp.BoundBox)
        except Exception:
            pass
    # Fallback: visible/hidden edge accessors
    for meth in ('getVisibleEdges', 'getHiddenEdges'):
        fn = getattr(view, meth, None)
        if fn is None:
            continue
        try:
            edges = fn()
            if edges:
                import Part
                comp = Part.makeCompound(edges)
                if comp.BoundBox.isValid():
                    candidates.append(comp.BoundBox)
        except Exception:
            pass
    if not candidates:
        return None
    bb = candidates[0]
    for extra in candidates[1:]:
        bb.add(extra)
    # TechDraw view-local geometry is centred on the view origin (0,0)
    hw = max(abs(bb.XMin), abs(bb.XMax))
    hh = max(abs(bb.YMin), abs(bb.YMax))
    return math.sqrt(hw * hw + hh * hh), hw, hh

def _get_page(doc, view):
    for p in doc.Objects:
        if p.TypeId != 'TechDraw::DrawPage':
            continue
        try:
            if view in p.Views:
                return p
        except Exception:
            pass
    for inobj in getattr(view, 'InList', []):
        if inobj.TypeId == 'TechDraw::DrawProjGroup':
            for p2 in getattr(inobj, 'InList', []):
                if p2.TypeId == 'TechDraw::DrawPage':
                    return p2
    return None

# ============================================================
# BUBBLE PLACEMENT
# ============================================================
def _repel(bubbles, min_sep, iterations=80):
    """In-place repulsion so bubbles don't overlap (bubbles = [[sno, bx, by], ...])."""
    for _ in range(iterations):
        moved = False
        for i in range(len(bubbles)):
            for j in range(i + 1, len(bubbles)):
                dx = bubbles[i][1] - bubbles[j][1]
                dy = bubbles[i][2] - bubbles[j][2]
                d  = math.sqrt(dx * dx + dy * dy)
                if 0.01 < d < min_sep:
                    push = (min_sep - d) * 0.5 + 0.1
                    ux, uy = dx / d, dy / d
                    bubbles[i][1] += ux * push
                    bubbles[i][2] += uy * push
                    bubbles[j][1] -= ux * push
                    bubbles[j][2] -= uy * push
                    moved = True
        if not moved:
            break

def place_perimeter(items, ring_r):
    """
    Creo-style auto-balloon layout.  Each balloon's ARROW TIP lands on the
    part's true projected 2D position; the BUBBLE sits on a ring that
    ENCLOSES the whole drawing, evenly spaced and sorted by angle so leader
    lines fan out neatly and rarely cross.

    Because the ring is sized to the drawing extent (not to the part-centre
    spread), tightly-packed parts still get distinct, well-separated bubbles
    around the outside — exactly how Creo/SolidWorks place BOM balloons.

    items  = [(sno, x2d, y2d), ...]  view-relative mm (centre = 0,0)
    ring_r = radius enclosing the drawing
    Returns [(sno, origin_x, origin_y, bx, by), ...]  view-relative mm.
    """
    n = len(items)
    if n == 0:
        return []

    # Sort by the angle of each part from the drawing centre; bubbles then
    # sit in the same angular order → leaders don't tangle.
    def _ang(it):
        _, x, y = it
        return math.atan2(y, x) if (x * x + y * y) > 1.0 else 0.0

    ordered = sorted(items, key=_ang)

    out = []
    for i, (sno, x2d, y2d) in enumerate(ordered):
        # Evenly spaced slot on the ring, starting at 12 o'clock, clockwise
        slot = -math.pi / 2.0 + 2.0 * math.pi * i / n
        bx = ring_r * math.cos(slot)
        by = ring_r * math.sin(slot)
        out.append((sno, x2d, y2d, bx, by))
    return out

def place_column(view_half_w, items):
    """
    Degenerate fallback: parts don't spread (single part, or no placements
    resolved).  Lay balloons in a numbered column beside the view centre.
    items = [(sno, x2d, y2d), ...]  view-relative mm.
    """
    n = len(items)
    row_h = 12.0
    grid_x = view_half_w + 28.0
    grid_y = (n - 1) * row_h / 2.0
    out = []
    for i, (sno, x2d, y2d) in enumerate(items):
        by = grid_y - i * row_h
        out.append((sno, x2d, y2d, grid_x, by))
    return out

# ============================================================
# MAIN
# ============================================================
def main():
    doc = App.ActiveDocument
    if not doc:
        QtWidgets.QMessageBox.warning(None, 'Error', 'No active document.')
        return

    sel_views = [o for o in Gui.Selection.getSelection() if o.TypeId in _VIEW_TYPES]
    if not sel_views:
        QtWidgets.QMessageBox.information(
            None, 'Select Views First',
            'Click one or more 3D views on the TechDraw sheet first,\n'
            'then run Balloon Assembly.\n\n'
            'Tip: hold Ctrl and click to select multiple views.')
        return

    rows = get_rows(doc)
    if not rows:
        QtWidgets.QMessageBox.warning(None, 'No Parts',
            'No assembly parts found. Open the assembly document first.')
        return

    from FreeCAD import Vector

    def _extent_of(nmap):
        """(all_corner_pts, centre3d) for a name_map — the drawing extent used
        to size the balloon ring and set the projection reference point."""
        pts = []
        for entries in nmap.values():
            for centre, corners in entries:
                if corners:
                    pts.extend(corners)
                elif centre is not None:
                    pts.append(centre)
        if pts:
            c3d = Vector(
                (min(p.x for p in pts) + max(p.x for p in pts)) / 2.0,
                (min(p.y for p in pts) + max(p.y for p in pts)) / 2.0,
                (min(p.z for p in pts) + max(p.z for p in pts)) / 2.0)
        else:
            c3d = Vector(0, 0, 0)
        return pts, c3d

    # Assembled part positions (used for ordinary views).  Exploded positions
    # are read READ-ONLY from the ExplodedView and used ONLY for views that
    # project an exploded view — so balloon tips follow the parts to their
    # separated locations instead of collapsing onto stacked assembled centres.
    name_map_asm = get_instances(doc)
    exp_plc = _exploded_placements(doc)
    name_map_exp = get_instances(doc, exp_plc) if exp_plc else None
    App.Console.PrintMessage(
        '[BalloonAssembly] resolved {} parts (assembled); exploded placements '
        'available for {} parts\n'.format(len(name_map_asm), len(exp_plc)))

    # Remove existing BNC balloons
    for obj in list(doc.Objects):
        if (obj.TypeId == 'TechDraw::DrawViewBalloon'
                and obj.Name.startswith(BALLOON_PREFIX)):
            try:
                doc.removeObject(obj.Name)
            except Exception:
                pass

    # Distribute rows across selected views
    n_views  = len(sel_views)
    total    = len(rows)
    per_view = int(math.ceil(total / float(n_views)))
    chunks   = []
    for vi in range(n_views):
        start = vi * per_view
        end   = min(start + per_view, total)
        chunks.append([(start + i + 1, rows[start + i]) for i in range(end - start)])

    pages_seen    = set()
    total_created = 0
    layout_used   = 'perimeter'

    for view, chunk in zip(sel_views, chunks):
        if not chunk:
            continue
        page = _get_page(doc, view)
        if page is None:
            continue

        # TechDraw balloon X/Y/OriginX/OriginY are stored RELATIVE TO THE
        # VIEW CENTRE (the balloon is a child of the view's scene item), NOT
        # in absolute page coordinates.  Adding view.X/view.Y here is what
        # pushed every balloon off into the page corner.  Reference is 0,0.
        view_x = 0.0
        view_y = 0.0
        xd, yd = _view_axes(view)
        scale  = _view_scale(view)

        # Pick exploded vs assembled positions for THIS view.  A view whose
        # Source is an exploded view must use the exploded part positions or
        # its balloon tips land on the assembled (stacked) locations.
        exploded = bool(name_map_exp) and _view_sources_exploded(view)
        name_map = name_map_exp if exploded else name_map_asm
        all_pts, centre3d = _extent_of(name_map)
        App.Console.PrintMessage(
            '[BalloonAssembly] view "{}": using {} part positions\n'.format(
                view.Label, 'EXPLODED' if exploded else 'assembled'))

        # ---- Resolve each part's WORLD geometry (centre + bbox corners) ----
        # One balloon per PHYSICAL INSTANCE — a Qty>1 BOM row (e.g. 8
        # identical bolts) gets one entry per bolt here, not just one for
        # the whole row, so every instance gets its own leader/bubble.
        raw = []   # (sno, world_centre or None, corners or None)
        missing = []
        for sno, (pn, desc, qty) in chunk:
            entries = match_all_geom(pn, name_map)
            if entries:
                for c, corners in entries:
                    raw.append((sno, c, corners))
            else:
                raw.append((sno, None, None))
                missing.append(pn)

        def _proj(p):
            rel = p.sub(centre3d)
            return rel.dot(xd) * scale, rel.dot(yd) * scale

        # Arrow-tip position per part (projected part centre, view-relative)
        items = []
        for sno, c, corners in raw:
            if c is not None:
                x2d, y2d = _proj(c)
            else:
                x2d, y2d = 0.0, 0.0
            items.append((sno, x2d, y2d))

        # Radius of my projected assembled geometry (from all instances)
        geom_r = 0.0
        for p in all_pts:
            px, py = _proj(p)
            geom_r = max(geom_r, math.sqrt(px * px + py * py))

        # GROUND TRUTH: the view's actual drawn 2D extent.  For exploded
        # views this is far larger than the assembled geometry, so we size
        # the ring to it and scale the tips outward to reach the spread parts.
        ext = _view_extent_2d(view)
        tip_scale = 1.0
        if ext is not None and ext[0] > 1.0:
            drawn_r = ext[0]
            # Only treat this as an exploded view once the drawn extent is
            # SUBSTANTIALLY bigger than the assembled geometry (>1.5x) — a
            # smaller gap is more likely measurement slack (e.g. HLR edge
            # noise) than an actual explosion, and stretching every tip for
            # a small gap does more harm (misaligning correct tips) than
            # good.
            if geom_r > 1.0 and drawn_r > geom_r * 1.5:
                tip_scale = drawn_r / geom_r
            draw_r = drawn_r
        else:
            draw_r = geom_r

        if tip_scale != 1.0:
            items = [(sno, x * tip_scale, y * tip_scale) for sno, x, y in items]

        ring_r = max(draw_r + PERIM_MARGIN, PERIM_RADIUS_MIN)
        App.Console.PrintMessage(
            '[BalloonAssembly] geom_r={:.1f}mm, drawn_r={}, tip_scale={:.2f}\n'.format(
                geom_r, ('%.1fmm' % ext[0]) if ext else 'n/a', tip_scale))

        # ---- Diagnostics ----
        spread = max((math.sqrt(x*x + y*y) for _, x, y in items), default=0.0)
        n_matched = sum(1 for _, c, _ in raw if c is not None)
        App.Console.PrintMessage(
            '[BalloonAssembly] view "{}": {}/{} balloons located, scale={:.3f}, '
            'centre-spread={:.1f}mm, drawing radius={:.1f}mm, ring={:.1f}mm\n'.format(
                view.Label, n_matched, len(raw), scale, spread, draw_r, ring_r))
        if missing:
            App.Console.PrintWarning(
                '[BalloonAssembly] NOT located (no placement match): {}\n'.format(
                    ', '.join(missing[:30])))

        if draw_r >= SPREAD_THRESHOLD:
            placements  = place_perimeter(items, ring_r)
            layout_used = 'perimeter'
        else:
            view_half_w = max(spread + 20.0, 50.0)
            placements  = place_column(view_half_w, items)
            layout_used = 'column'

        # ---- Create TechDraw balloon objects ----
        for sno, origin_x, origin_y, bx, by in placements:
            name = '{}{:03d}'.format(BALLOON_PREFIX, sno)
            b = doc.addObject('TechDraw::DrawViewBalloon', name)
            b.SourceView = view
            b.Text       = str(sno)
            # All coordinate properties must be Quantity — plain floats
            # break TechDraw's drag-to-move handler
            b.OriginX    = _mm(origin_x)
            b.OriginY    = _mm(origin_y)
            b.X          = _mm(bx)
            b.Y          = _mm(by)
            try:
                b.BubbleShape = 0   # 0 = Circular
            except AttributeError:
                pass
            try:
                b.ViewObject.FontSize  = _mm(3.5)
                b.ViewObject.LineWidth = 0.5
            except Exception:
                pass
            page.addView(b)
            total_created += 1

        pages_seen.add(page.Name)

    # Recompute only affected pages
    to_recompute = [doc.getObject(nm) for nm in pages_seen if doc.getObject(nm)]
    try:
        doc.recompute(to_recompute if to_recompute else [])
    except Exception:
        doc.recompute()

    view_labels = ', '.join(v.Label for v in sel_views)

    if layout_used == 'column':
        tip = (
            'Parts did not spread in this view (single part or placements\n'
            'could not be resolved) — balloons placed in a column beside it.\n\n'
            'Drag each numbered circle onto its part.\n\n'
            'Numbers match the Assembly Table S.No column.\n'
            'Re-run to regenerate after assembly changes.'
        )
    else:
        tip = (
            'Each leader points at the part\'s real position in the view;\n'
            'bubbles are spread around the view perimeter (Creo-style).\n\n'
            'TO FINE-TUNE:\n'
            '  Click the numbered circle to select it, then drag.\n\n'
            'Numbers match the Assembly Table S.No column.\n'
            'Re-run to regenerate after assembly changes.'
        )

    QtWidgets.QMessageBox.information(
        None, 'Balloons Created — BNC CAD',
        '{} balloons on: {}\n\n{}'.format(total_created, view_labels, tip))


main()
